FME workspace shp_to_gml_nanaimo v25.fmw

Parameters:
- SourceDataset_ESRISHAPE = $(FME_MF_DIR)Input\Data processing with QGIS\Pipes_subset.shp   # Source Esri Shapefile(s)
- SourceDataset_ESRISHAPE_9 = C:\Users\FF\UT\Thesis\04-Models\Test02_NanaimoSHP\Input\Data processing with QGIS\Appurtenances_subset.shp   # Source Esri Shapefile(s)
- SourceDataset_ESRISHAPE_6 = C:\Users\FF\UT\Thesis\04-Models\Test02_NanaimoSHP\Input\Data processing with QGIS\Pipes_subset_processed.shp   # Source Esri Shapefile(s)
- SourceDataset_ESRISHAPE_7 = C:\Users\FF\UT\Thesis\04-Models\Test02_NanaimoSHP\Input\Data processing with QGIS\Pipes_subset_few_pipes.shp   # Source Esri Shapefile(s)
- SourceDataset_ESRISHAPE_8 = C:\Users\FF\UT\Thesis\04-Models\Test02_NanaimoSHP\Input\Data processing with QGIS\appurtenance_subset_few_pipes.shp   # Source Esri Shapefile(s)
- SourceDataset_GEOTIFF_3 = C:\Users\FF\UT\Thesis\04-Models\Test02_NanaimoSHP\Input\DEM nanaimo 4\reprojectedDEM.tif   # Source GeoTIFF File(s)
- DestDataset_CITYGML = C:\Users\FF\UT\Thesis\04-Models\Test02_NanaimoSHP\Output\Test_nanaimo_0.9.2 v04.gml   # Destination CityGML Document

Readers:
- ESRISHAPE_1: ESRISHAPE from $(SourceDataset_ESRISHAPE)
- ESRISHAPE_2: ESRISHAPE from $(SourceDataset_ESRISHAPE_9)
- ESRISHAPE_3: ESRISHAPE from $(SourceDataset_ESRISHAPE_6)
- ESRISHAPE_4: ESRISHAPE from $(SourceDataset_ESRISHAPE_7)
- ESRISHAPE_5: ESRISHAPE from $(SourceDataset_ESRISHAPE_8)
- GEOTIFF_1: GEOTIFF from $(SourceDataset_GEOTIFF_3)

Writers:
- CITYGML_1: CITYGML to $(DestDataset_CITYGML)

utility_Network (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), utility_medium_supply{}.utility_electrical_medium_supply_utility_potential_supply_utility_supply_utility_flow_rate xml_real64, utility_medium_supply{}.utility_electrical_medium_supply_utility_potential_supply_utility_supply_utility_flow_rate_units xml_buffer, utility_medium_supply{}.utility_electrical_medium_supply_utility_potential_supply_utility_supply_utility_status xml_char(16), utility_medium_supply{}.utility_electrical_medium_supply_utility_current_supply_utility_supply_utility_flow_rate xml_real64, utility_medium_supply{}.utility_electrical_medium_supply_utility_current_supply_utility_supply_utility_flow_rate_units xml_buffer, utility_medium_supply{}.utility_electrical_medium_supply_utility_current_supply_utility_supply_utility_status xml_char(16), utility_medium_supply{}.utility_electrical_medium_supply_utility_storage{}.utility_storage_utility_type xml_buffer, utility_medium_supply{}.utility_electrical_medium_supply_utility_storage{}.utility_storage_utility_type_codeSpace xml_buffer, utility_medium_supply{}.utility_electrical_medium_supply_utility_storage{}.utility_storage_utility_max_capacity xml_real64, utility_medium_supply{}.utility_electrical_medium_supply_utility_storage{}.utility_storage_utility_max_capacity_units xml_buffer, utility_medium_supply{}.utility_electrical_medium_supply_utility_storage{}.utility_storage_utility_fill_level xml_real64, utility_medium_supply{}.utility_electrical_medium_supply_utility_storage{}.utility_storage_utility_inflow_rate xml_real64, utility_medium_supply{}.utility_electrical_medium_supply_utility_storage{}.utility_storage_utility_inflow_rate_units xml_buffer, utility_medium_supply{}.utility_electrical_medium_supply_utility_storage{}.utility_storage_utility_outflow_rate xml_real64, utility_medium_supply{}.utility_electrical_medium_supply_utility_storage{}.utility_storage_utility_outflow_rate_units xml_buffer, utility_medium_supply{}.utility_electrical_medium_supply_utility_type xml_char(29),
      utility_medium_supply{}.utility_gaseous_medium_supply_utility_potential_supply_utility_supply_utility_flow_rate xml_real64, utility_medium_supply{}.utility_gaseous_medium_supply_utility_potential_supply_utility_supply_utility_flow_rate_units xml_buffer, utility_medium_supply{}.utility_gaseous_medium_supply_utility_potential_supply_utility_supply_utility_status xml_char(16), utility_medium_supply{}.utility_gaseous_medium_supply_utility_current_supply_utility_supply_utility_flow_rate xml_real64, utility_medium_supply{}.utility_gaseous_medium_supply_utility_current_supply_utility_supply_utility_flow_rate_units xml_buffer, utility_medium_supply{}.utility_gaseous_medium_supply_utility_current_supply_utility_supply_utility_status xml_char(16), utility_medium_supply{}.utility_gaseous_medium_supply_utility_storage{}.utility_storage_utility_type xml_buffer, utility_medium_supply{}.utility_gaseous_medium_supply_utility_storage{}.utility_storage_utility_type_codeSpace xml_buffer, utility_medium_supply{}.utility_gaseous_medium_supply_utility_storage{}.utility_storage_utility_max_capacity xml_real64, utility_medium_supply{}.utility_gaseous_medium_supply_utility_storage{}.utility_storage_utility_max_capacity_units xml_buffer, utility_medium_supply{}.utility_gaseous_medium_supply_utility_storage{}.utility_storage_utility_fill_level xml_real64, utility_medium_supply{}.utility_gaseous_medium_supply_utility_storage{}.utility_storage_utility_inflow_rate xml_real64, utility_medium_supply{}.utility_gaseous_medium_supply_utility_storage{}.utility_storage_utility_inflow_rate_units xml_buffer, utility_medium_supply{}.utility_gaseous_medium_supply_utility_storage{}.utility_storage_utility_outflow_rate xml_real64, utility_medium_supply{}.utility_gaseous_medium_supply_utility_storage{}.utility_storage_utility_outflow_rate_units xml_buffer, utility_medium_supply{}.utility_gaseous_medium_supply_utility_type xml_buffer, utility_medium_supply{}.utility_gaseous_medium_supply_utility_type_codeSpace xml_buffer, utility_medium_supply{}.utility_liquid_medium_supply_utility_potential_supply_utility_supply_utility_flow_rate xml_real64, utility_medium_supply{}.utility_liquid_medium_supply_utility_potential_supply_utility_supply_utility_flow_rate_units xml_buffer, utility_medium_supply{}.utility_liquid_medium_supply_utility_potential_supply_utility_supply_utility_status xml_char(16), utility_medium_supply{}.utility_liquid_medium_supply_utility_current_supply_utility_supply_utility_flow_rate xml_real64, utility_medium_supply{}.utility_liquid_medium_supply_utility_current_supply_utility_supply_utility_flow_rate_units xml_buffer, utility_medium_supply{}.utility_liquid_medium_supply_utility_current_supply_utility_supply_utility_status xml_char(16), utility_medium_supply{}.utility_liquid_medium_supply_utility_storage{}.utility_storage_utility_type xml_buffer, utility_medium_supply{}.utility_liquid_medium_supply_utility_storage{}.utility_storage_utility_type_codeSpace xml_buffer, utility_medium_supply{}.utility_liquid_medium_supply_utility_storage{}.utility_storage_utility_max_capacity xml_real64, utility_medium_supply{}.utility_liquid_medium_supply_utility_storage{}.utility_storage_utility_max_capacity_units xml_buffer, utility_medium_supply{}.utility_liquid_medium_supply_utility_storage{}.utility_storage_utility_fill_level xml_real64, utility_medium_supply{}.utility_liquid_medium_supply_utility_storage{}.utility_storage_utility_inflow_rate xml_real64, utility_medium_supply{}.utility_liquid_medium_supply_utility_storage{}.utility_storage_utility_inflow_rate_units xml_buffer,
      utility_medium_supply{}.utility_liquid_medium_supply_utility_storage{}.utility_storage_utility_outflow_rate xml_real64, utility_medium_supply{}.utility_liquid_medium_supply_utility_storage{}.utility_storage_utility_outflow_rate_units xml_buffer, utility_medium_supply{}.utility_liquid_medium_supply_utility_type xml_buffer, utility_medium_supply{}.utility_liquid_medium_supply_utility_type_codeSpace xml_buffer, utility_medium_supply{}.utility_optical_medium_supply_utility_potential_supply_utility_supply_utility_flow_rate xml_real64, utility_medium_supply{}.utility_optical_medium_supply_utility_potential_supply_utility_supply_utility_flow_rate_units xml_buffer, utility_medium_supply{}.utility_optical_medium_supply_utility_potential_supply_utility_supply_utility_status xml_char(16), utility_medium_supply{}.utility_optical_medium_supply_utility_current_supply_utility_supply_utility_flow_rate xml_real64, utility_medium_supply{}.utility_optical_medium_supply_utility_current_supply_utility_supply_utility_flow_rate_units xml_buffer, utility_medium_supply{}.utility_optical_medium_supply_utility_current_supply_utility_supply_utility_status xml_char(16), utility_medium_supply{}.utility_optical_medium_supply_utility_storage{}.utility_storage_utility_type xml_buffer, utility_medium_supply{}.utility_optical_medium_supply_utility_storage{}.utility_storage_utility_type_codeSpace xml_buffer, utility_medium_supply{}.utility_optical_medium_supply_utility_storage{}.utility_storage_utility_max_capacity xml_real64, utility_medium_supply{}.utility_optical_medium_supply_utility_storage{}.utility_storage_utility_max_capacity_units xml_buffer, utility_medium_supply{}.utility_optical_medium_supply_utility_storage{}.utility_storage_utility_fill_level xml_real64, utility_medium_supply{}.utility_optical_medium_supply_utility_storage{}.utility_storage_utility_inflow_rate xml_real64, utility_medium_supply{}.utility_optical_medium_supply_utility_storage{}.utility_storage_utility_inflow_rate_units xml_buffer, utility_medium_supply{}.utility_optical_medium_supply_utility_storage{}.utility_storage_utility_outflow_rate xml_real64, utility_medium_supply{}.utility_optical_medium_supply_utility_storage{}.utility_storage_utility_outflow_rate_units xml_buffer, utility_medium_supply{}.utility_optical_medium_supply_utility_type xml_char(7), utility_medium_supply{}.utility_solid_medium_supply_utility_potential_supply_utility_supply_utility_flow_rate xml_real64, utility_medium_supply{}.utility_solid_medium_supply_utility_potential_supply_utility_supply_utility_flow_rate_units xml_buffer, utility_medium_supply{}.utility_solid_medium_supply_utility_potential_supply_utility_supply_utility_status xml_char(16), utility_medium_supply{}.utility_solid_medium_supply_utility_current_supply_utility_supply_utility_flow_rate xml_real64, utility_medium_supply{}.utility_solid_medium_supply_utility_current_supply_utility_supply_utility_flow_rate_units xml_buffer, utility_medium_supply{}.utility_solid_medium_supply_utility_current_supply_utility_supply_utility_status xml_char(16), utility_medium_supply{}.utility_solid_medium_supply_utility_storage{}.utility_storage_utility_type xml_buffer, utility_medium_supply{}.utility_solid_medium_supply_utility_storage{}.utility_storage_utility_type_codeSpace xml_buffer, utility_medium_supply{}.utility_solid_medium_supply_utility_storage{}.utility_storage_utility_max_capacity xml_real64, utility_medium_supply{}.utility_solid_medium_supply_utility_storage{}.utility_storage_utility_max_capacity_units xml_buffer,
      utility_medium_supply{}.utility_solid_medium_supply_utility_storage{}.utility_storage_utility_fill_level xml_real64, utility_medium_supply{}.utility_solid_medium_supply_utility_storage{}.utility_storage_utility_inflow_rate xml_real64, utility_medium_supply{}.utility_solid_medium_supply_utility_storage{}.utility_storage_utility_inflow_rate_units xml_buffer, utility_medium_supply{}.utility_solid_medium_supply_utility_storage{}.utility_storage_utility_outflow_rate xml_real64, utility_medium_supply{}.utility_solid_medium_supply_utility_storage{}.utility_storage_utility_outflow_rate_units xml_buffer, utility_medium_supply{}.utility_solid_medium_supply_utility_type xml_buffer, utility_medium_supply{}.utility_solid_medium_supply_utility_type_codeSpace xml_buffer, utility_medium_supply{}.utility_abstract_medium_supply_utility_potential_supply_utility_supply_utility_flow_rate xml_real64, utility_medium_supply{}.utility_abstract_medium_supply_utility_potential_supply_utility_supply_utility_flow_rate_units xml_buffer, utility_medium_supply{}.utility_abstract_medium_supply_utility_potential_supply_utility_supply_utility_status xml_char(16), utility_medium_supply{}.utility_abstract_medium_supply_utility_current_supply_utility_supply_utility_flow_rate xml_real64, utility_medium_supply{}.utility_abstract_medium_supply_utility_current_supply_utility_supply_utility_flow_rate_units xml_buffer, utility_medium_supply{}.utility_abstract_medium_supply_utility_current_supply_utility_supply_utility_status xml_char(16), utility_medium_supply{}.utility_abstract_medium_supply_utility_storage{}.utility_storage_utility_type xml_buffer, utility_medium_supply{}.utility_abstract_medium_supply_utility_storage{}.utility_storage_utility_type_codeSpace xml_buffer, utility_medium_supply{}.utility_abstract_medium_supply_utility_storage{}.utility_storage_utility_max_capacity xml_real64, utility_medium_supply{}.utility_abstract_medium_supply_utility_storage{}.utility_storage_utility_max_capacity_units xml_buffer, utility_medium_supply{}.utility_abstract_medium_supply_utility_storage{}.utility_storage_utility_fill_level xml_real64, utility_medium_supply{}.utility_abstract_medium_supply_utility_storage{}.utility_storage_utility_inflow_rate xml_real64, utility_medium_supply{}.utility_abstract_medium_supply_utility_storage{}.utility_storage_utility_inflow_rate_units xml_buffer, utility_medium_supply{}.utility_abstract_medium_supply_utility_storage{}.utility_storage_utility_outflow_rate xml_real64, utility_medium_supply{}.utility_abstract_medium_supply_utility_storage{}.utility_storage_utility_outflow_rate_units xml_buffer, utility_role_in_network{}.xlink_href xml_buffer, citygml_appearance{}.xlink_href xml_buffer, utility_class xml_buffer, utility_class_codeSpace xml_buffer, utility_function{} xml_buffer, utility_function{}.codeSpace xml_buffer, utility_usage{} xml_buffer, utility_usage{}.codeSpace xml_buffer,
      utility_transported_medium_xlink_href xml_buffer, utility_sub_network{}.xlink_href xml_buffer, utility_topo_graph_xlink_href xml_buffer, utility_component{}.xlink_href xml_buffer, utility_supplies_xlink_href xml_buffer, utility_sub_ordinate_network{}.xlink_href xml_buffer, utility_super_ordinate_network{}.xlink_href xml_buffer
utility_NetworkGraph (writer CITYGML_1)
    attributes: citygml_target_uri xml_buffer, citygml_feature_role xml_buffer, citygml_feature_role_attr_name xml_buffer, citygml_feature_role_attr_val xml_buffer, gml_description xml_buffer, gml_name xml_buffer, utility_feature_graph_member{}.xlink_href xml_buffer, utility_link_member{}.xlink_href xml_buffer, utility_network_link_member{}.xlink_href xml_buffer
utility_LiquidMedium (writer CITYGML_1)
    attributes: citygml_target_uri xml_buffer, citygml_feature_role xml_buffer, citygml_feature_role_attr_name xml_buffer, citygml_feature_role_attr_val xml_buffer, gml_description xml_buffer, gml_name xml_buffer, utility_owner xml_buffer, utility_is_classified_by{}.xlink_href xml_buffer, utility_associated_network{}.xlink_href xml_buffer, utility_type xml_buffer, utility_type_codeSpace xml_buffer, utility_is_corrosive xml_boolean, utility_is_explosive xml_boolean, utility_flammable xml_real64, utility_electric_conductivity xml_buffer, utility_electric_conductivity_units xml_buffer, utility_ph_value_range xml_buffer, utility_ph_value_range_units xml_buffer, utility_temperature_range xml_buffer, utility_temperature_range_units xml_buffer, utility_flow_rate_range xml_buffer, utility_flow_rate_range_units xml_buffer, utility_pressure_range xml_buffer, utility_pressure_range_units xml_buffer
Junction_2
    -> FM_AddNetworkID_AddNEtworkGraphID_ToPipes [SUPPLIER]
    -> FeaMer_AddNetworkID_AddNEtworkGraphID_ToAppurtenances [SUPPLIER]
Note: NOTES: / 1) The network chosen is a segment of the storm sewer network from Nanaimo. / 2) There are four 'ranks' of pipes: (1) Mains, (2) Service lines, (3) Lead lines, and (4) Lead2 lines. / 3) There are some appurtenances available in the shapefiles but two important types of connections are missing in the file: / a) the fittings when a secondary line intersects a principal one (typical situation of house connections), and / b) some fittings at places where two lines are adjoining (and there is no appurtenance information at this location in the shapefile). / 4) Topology: / a) Mains are intersected by Service and Lead lines. Related to 3a) / b) Lead lines are intersected by Lead2 lines. Related to 3a) / c) End-to-end connections of Lead and Service lines: No appurtenance available in the shapefiles. In other words, some adjoining lines lack an appurtenance such as a fitting or manhole. Related to 3b). / Therefore, two types of fittings need to be added (intersecting and adjoining)
Note: 1) Creating Network and Network Graph
Note: 2) Reading pipe shapefile
Pipes_subset_processed (reader ESRISHAPE_3)
    attributes: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
Pipes_subset_few_pipes (reader ESRISHAPE_4)
    attributes: TYPE char(20), DIAMETER number(11,0), MATERIAL char(20), OWNER char(20), YEAR long, ASBUILT number(11,0), ACCURACY char(20), LENGTH number(31,15), STARTID number(11,0), ENDID number(11,0), STARTELEV number(31,15), ENDELEV number(31,15), STARTINV number(31,15), ENDINV number(31,15), PIPEID number(11,0), GID number(11,0)
    -> FM_AddNetworkID_AddNEtworkGraphID_ToPipes [REQUESTOR]
Note: 3) Overlaying lines that cross each other outside of the end-nodes (along the pipe)
FM_AddNetworkID_AddNEtworkGraphID_ToPipes: FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> LineOnLineOverlayer [LINE]
    MERGED -> AttributeFilter
    MERGED -> AttributeFilter_4
Note: 4) Topology of each separate type of pipe
AttributeFilter
    ATTR_NAME = TYPE
    ATTR_VALUES = <Empty>,<Missing>,<Null>,<Unfiltered>,Main,Service,Lead,Lead2
    Main -> TopB_MainLines
    Service -> TopB_ServiceLines
    Lead -> TopB_LeadLines
    Lead2 -> TopB_Lead2Lines
Note: FeatureMerger_2 : Requestor
Junction_3
    -> Junction_8
Note: 6) Topology of the now topologically correct network
Note: FeatureMerger_2 : Requestor
Note: 7) Merging and filtering to keep only 'whole' pipes, as opposed to the parts that make a pipe which is segmented in the complete topology
Junction_8
    -> Junction_9
Note: 12) Using merges to determine the InterFeatureLinks
Note: 14) Relating nodes to the pipe FeatureGraph they belong to
Note: 13) Using merges to determine the INTERIOR nodes of pipes
Note: Junction_3 : Output
Junction_9
    -> FeatureMerger_2 [REQUESTOR]
Topology_nodes: Inspector
appurtenance_subset_few_pipes (reader ESRISHAPE_5)
    attributes: TYPE char(25), SUBTYPE char(20), OWNER char(20), YEAR short, ASBUILT long, ACCURACY char(20), NODEELEV float, DEPTH float, NODEID number(11,0), GID number(11,0)
    -> FeaMer_AddNetworkID_AddNEtworkGraphID_ToAppurtenances [REQUESTOR]
Note: 5) Reading manhole shapefile
FeaMer_AddNetworkID_AddNEtworkGraphID_ToAppurtenances: FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> NeighborFinder [BASE]
    MERGED -> TestFilter__ID_Of_Exit_Poinf_Of_Network
    MERGED -> Fittings_between_connecting_pipes [Filter]
    MERGED -> 3DForcer
TestFilter__ID_Of_Exit_Poinf_Of_Network
    DEFAULT_VALUE = <UNFILTERED>
    TEST_LIST = "BOOL_OP,OR,COMPOSITE_TEST,""""""1"""""",TEST_CLAUSE,TEST @Value(NODEID) != 22977", !=
    <UNFILTERED> -> NetworkFlowOrientor [DESTINATION]
DuplicateFilter
    INPUT_ORDERED_CHOICE = No
    KEYATTR = MATERIAL
    UNIQUE -> UUIDGenerator_MaterialID
utility_ExteriorMaterial (writer CITYGML_1)
    attributes: citygml_target_uri xml_buffer, citygml_feature_role xml_buffer, citygml_feature_role_attr_name xml_buffer, citygml_feature_role_attr_val xml_buffer, gml_description xml_buffer, gml_name xml_buffer, utility_type xml_buffer, utility_type_codeSpace xml_buffer, utility_consists_of_fm{}.xlink_href xml_buffer, utility_consists_of{}.xlink_href xml_buffer, utility_is_classified_by{}.xlink_href xml_buffer, utility_used_by{}.xlink_href xml_buffer
Note: StrCon_10 : Output
Junction_5
    -> FeatureMerger_Material [REQUESTOR]
FeatureMerger_Material
    ATTR_ACCUM_MODE = Merge Supplier
    ATTR_CONFLICT_RES = Use Requestor
    IGNORE_NULLS = No
    JOIN_KEYS = @Value(MATERIAL) @Value(MATERIAL) AUTO
    MERGE_TYPE = Attributes Only
    PROCESS_DUPS = NO
    REJECT_NULL_MISSING_KEYS = No
    SUPPLIERS_FIRST = No
    MERGED -> AttributeCreator
utility_RoundPipe (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), utility_medium_supply{}.utility_electrical_medium_supply_utility_potential_supply_utility_supply_utility_flow_rate xml_real64, utility_medium_supply{}.utility_electrical_medium_supply_utility_potential_supply_utility_supply_utility_flow_rate_units xml_buffer, utility_medium_supply{}.utility_electrical_medium_supply_utility_potential_supply_utility_supply_utility_status xml_char(16), utility_medium_supply{}.utility_electrical_medium_supply_utility_current_supply_utility_supply_utility_flow_rate xml_real64, utility_medium_supply{}.utility_electrical_medium_supply_utility_current_supply_utility_supply_utility_flow_rate_units xml_buffer, utility_medium_supply{}.utility_electrical_medium_supply_utility_current_supply_utility_supply_utility_status xml_char(16), utility_medium_supply{}.utility_electrical_medium_supply_utility_storage{}.utility_storage_utility_type xml_buffer, utility_medium_supply{}.utility_electrical_medium_supply_utility_storage{}.utility_storage_utility_type_codeSpace xml_buffer, utility_medium_supply{}.utility_electrical_medium_supply_utility_storage{}.utility_storage_utility_max_capacity xml_real64, utility_medium_supply{}.utility_electrical_medium_supply_utility_storage{}.utility_storage_utility_max_capacity_units xml_buffer, utility_medium_supply{}.utility_electrical_medium_supply_utility_storage{}.utility_storage_utility_fill_level xml_real64, utility_medium_supply{}.utility_electrical_medium_supply_utility_storage{}.utility_storage_utility_inflow_rate xml_real64, utility_medium_supply{}.utility_electrical_medium_supply_utility_storage{}.utility_storage_utility_inflow_rate_units xml_buffer, utility_medium_supply{}.utility_electrical_medium_supply_utility_storage{}.utility_storage_utility_outflow_rate xml_real64, utility_medium_supply{}.utility_electrical_medium_supply_utility_storage{}.utility_storage_utility_outflow_rate_units xml_buffer, utility_medium_supply{}.utility_electrical_medium_supply_utility_type xml_char(29),
      utility_medium_supply{}.utility_gaseous_medium_supply_utility_potential_supply_utility_supply_utility_flow_rate xml_real64, utility_medium_supply{}.utility_gaseous_medium_supply_utility_potential_supply_utility_supply_utility_flow_rate_units xml_buffer, utility_medium_supply{}.utility_gaseous_medium_supply_utility_potential_supply_utility_supply_utility_status xml_char(16), utility_medium_supply{}.utility_gaseous_medium_supply_utility_current_supply_utility_supply_utility_flow_rate xml_real64, utility_medium_supply{}.utility_gaseous_medium_supply_utility_current_supply_utility_supply_utility_flow_rate_units xml_buffer, utility_medium_supply{}.utility_gaseous_medium_supply_utility_current_supply_utility_supply_utility_status xml_char(16), utility_medium_supply{}.utility_gaseous_medium_supply_utility_storage{}.utility_storage_utility_type xml_buffer, utility_medium_supply{}.utility_gaseous_medium_supply_utility_storage{}.utility_storage_utility_type_codeSpace xml_buffer, utility_medium_supply{}.utility_gaseous_medium_supply_utility_storage{}.utility_storage_utility_max_capacity xml_real64, utility_medium_supply{}.utility_gaseous_medium_supply_utility_storage{}.utility_storage_utility_max_capacity_units xml_buffer, utility_medium_supply{}.utility_gaseous_medium_supply_utility_storage{}.utility_storage_utility_fill_level xml_real64, utility_medium_supply{}.utility_gaseous_medium_supply_utility_storage{}.utility_storage_utility_inflow_rate xml_real64, utility_medium_supply{}.utility_gaseous_medium_supply_utility_storage{}.utility_storage_utility_inflow_rate_units xml_buffer, utility_medium_supply{}.utility_gaseous_medium_supply_utility_storage{}.utility_storage_utility_outflow_rate xml_real64, utility_medium_supply{}.utility_gaseous_medium_supply_utility_storage{}.utility_storage_utility_outflow_rate_units xml_buffer, utility_medium_supply{}.utility_gaseous_medium_supply_utility_type xml_buffer, utility_medium_supply{}.utility_gaseous_medium_supply_utility_type_codeSpace xml_buffer, utility_medium_supply{}.utility_liquid_medium_supply_utility_potential_supply_utility_supply_utility_flow_rate xml_real64, utility_medium_supply{}.utility_liquid_medium_supply_utility_potential_supply_utility_supply_utility_flow_rate_units xml_buffer, utility_medium_supply{}.utility_liquid_medium_supply_utility_potential_supply_utility_supply_utility_status xml_char(16), utility_medium_supply{}.utility_liquid_medium_supply_utility_current_supply_utility_supply_utility_flow_rate xml_real64, utility_medium_supply{}.utility_liquid_medium_supply_utility_current_supply_utility_supply_utility_flow_rate_units xml_buffer, utility_medium_supply{}.utility_liquid_medium_supply_utility_current_supply_utility_supply_utility_status xml_char(16), utility_medium_supply{}.utility_liquid_medium_supply_utility_storage{}.utility_storage_utility_type xml_buffer, utility_medium_supply{}.utility_liquid_medium_supply_utility_storage{}.utility_storage_utility_type_codeSpace xml_buffer, utility_medium_supply{}.utility_liquid_medium_supply_utility_storage{}.utility_storage_utility_max_capacity xml_real64, utility_medium_supply{}.utility_liquid_medium_supply_utility_storage{}.utility_storage_utility_max_capacity_units xml_buffer, utility_medium_supply{}.utility_liquid_medium_supply_utility_storage{}.utility_storage_utility_fill_level xml_real64, utility_medium_supply{}.utility_liquid_medium_supply_utility_storage{}.utility_storage_utility_inflow_rate xml_real64, utility_medium_supply{}.utility_liquid_medium_supply_utility_storage{}.utility_storage_utility_inflow_rate_units xml_buffer,
      utility_medium_supply{}.utility_liquid_medium_supply_utility_storage{}.utility_storage_utility_outflow_rate xml_real64, utility_medium_supply{}.utility_liquid_medium_supply_utility_storage{}.utility_storage_utility_outflow_rate_units xml_buffer, utility_medium_supply{}.utility_liquid_medium_supply_utility_type xml_buffer, utility_medium_supply{}.utility_liquid_medium_supply_utility_type_codeSpace xml_buffer, utility_medium_supply{}.utility_optical_medium_supply_utility_potential_supply_utility_supply_utility_flow_rate xml_real64, utility_medium_supply{}.utility_optical_medium_supply_utility_potential_supply_utility_supply_utility_flow_rate_units xml_buffer, utility_medium_supply{}.utility_optical_medium_supply_utility_potential_supply_utility_supply_utility_status xml_char(16), utility_medium_supply{}.utility_optical_medium_supply_utility_current_supply_utility_supply_utility_flow_rate xml_real64, utility_medium_supply{}.utility_optical_medium_supply_utility_current_supply_utility_supply_utility_flow_rate_units xml_buffer, utility_medium_supply{}.utility_optical_medium_supply_utility_current_supply_utility_supply_utility_status xml_char(16), utility_medium_supply{}.utility_optical_medium_supply_utility_storage{}.utility_storage_utility_type xml_buffer, utility_medium_supply{}.utility_optical_medium_supply_utility_storage{}.utility_storage_utility_type_codeSpace xml_buffer, utility_medium_supply{}.utility_optical_medium_supply_utility_storage{}.utility_storage_utility_max_capacity xml_real64, utility_medium_supply{}.utility_optical_medium_supply_utility_storage{}.utility_storage_utility_max_capacity_units xml_buffer, utility_medium_supply{}.utility_optical_medium_supply_utility_storage{}.utility_storage_utility_fill_level xml_real64, utility_medium_supply{}.utility_optical_medium_supply_utility_storage{}.utility_storage_utility_inflow_rate xml_real64, utility_medium_supply{}.utility_optical_medium_supply_utility_storage{}.utility_storage_utility_inflow_rate_units xml_buffer, utility_medium_supply{}.utility_optical_medium_supply_utility_storage{}.utility_storage_utility_outflow_rate xml_real64, utility_medium_supply{}.utility_optical_medium_supply_utility_storage{}.utility_storage_utility_outflow_rate_units xml_buffer, utility_medium_supply{}.utility_optical_medium_supply_utility_type xml_char(7), utility_medium_supply{}.utility_solid_medium_supply_utility_potential_supply_utility_supply_utility_flow_rate xml_real64, utility_medium_supply{}.utility_solid_medium_supply_utility_potential_supply_utility_supply_utility_flow_rate_units xml_buffer, utility_medium_supply{}.utility_solid_medium_supply_utility_potential_supply_utility_supply_utility_status xml_char(16), utility_medium_supply{}.utility_solid_medium_supply_utility_current_supply_utility_supply_utility_flow_rate xml_real64, utility_medium_supply{}.utility_solid_medium_supply_utility_current_supply_utility_supply_utility_flow_rate_units xml_buffer, utility_medium_supply{}.utility_solid_medium_supply_utility_current_supply_utility_supply_utility_status xml_char(16), utility_medium_supply{}.utility_solid_medium_supply_utility_storage{}.utility_storage_utility_type xml_buffer, utility_medium_supply{}.utility_solid_medium_supply_utility_storage{}.utility_storage_utility_type_codeSpace xml_buffer, utility_medium_supply{}.utility_solid_medium_supply_utility_storage{}.utility_storage_utility_max_capacity xml_real64, utility_medium_supply{}.utility_solid_medium_supply_utility_storage{}.utility_storage_utility_max_capacity_units xml_buffer,
      utility_medium_supply{}.utility_solid_medium_supply_utility_storage{}.utility_storage_utility_fill_level xml_real64, utility_medium_supply{}.utility_solid_medium_supply_utility_storage{}.utility_storage_utility_inflow_rate xml_real64, utility_medium_supply{}.utility_solid_medium_supply_utility_storage{}.utility_storage_utility_inflow_rate_units xml_buffer, utility_medium_supply{}.utility_solid_medium_supply_utility_storage{}.utility_storage_utility_outflow_rate xml_real64, utility_medium_supply{}.utility_solid_medium_supply_utility_storage{}.utility_storage_utility_outflow_rate_units xml_buffer, utility_medium_supply{}.utility_solid_medium_supply_utility_type xml_buffer, utility_medium_supply{}.utility_solid_medium_supply_utility_type_codeSpace xml_buffer, utility_medium_supply{}.utility_abstract_medium_supply_utility_potential_supply_utility_supply_utility_flow_rate xml_real64, utility_medium_supply{}.utility_abstract_medium_supply_utility_potential_supply_utility_supply_utility_flow_rate_units xml_buffer, utility_medium_supply{}.utility_abstract_medium_supply_utility_potential_supply_utility_supply_utility_status xml_char(16), utility_medium_supply{}.utility_abstract_medium_supply_utility_current_supply_utility_supply_utility_flow_rate xml_real64, utility_medium_supply{}.utility_abstract_medium_supply_utility_current_supply_utility_supply_utility_flow_rate_units xml_buffer, utility_medium_supply{}.utility_abstract_medium_supply_utility_current_supply_utility_supply_utility_status xml_char(16), utility_medium_supply{}.utility_abstract_medium_supply_utility_storage{}.utility_storage_utility_type xml_buffer, utility_medium_supply{}.utility_abstract_medium_supply_utility_storage{}.utility_storage_utility_type_codeSpace xml_buffer, utility_medium_supply{}.utility_abstract_medium_supply_utility_storage{}.utility_storage_utility_max_capacity xml_real64, utility_medium_supply{}.utility_abstract_medium_supply_utility_storage{}.utility_storage_utility_max_capacity_units xml_buffer, utility_medium_supply{}.utility_abstract_medium_supply_utility_storage{}.utility_storage_utility_fill_level xml_real64, utility_medium_supply{}.utility_abstract_medium_supply_utility_storage{}.utility_storage_utility_inflow_rate xml_real64, utility_medium_supply{}.utility_abstract_medium_supply_utility_storage{}.utility_storage_utility_inflow_rate_units xml_buffer, utility_medium_supply{}.utility_abstract_medium_supply_utility_storage{}.utility_storage_utility_outflow_rate xml_real64, utility_medium_supply{}.utility_abstract_medium_supply_utility_storage{}.utility_storage_utility_outflow_rate_units xml_buffer, utility_role_in_network{}.xlink_href xml_buffer, citygml_appearance{}.xlink_href xml_buffer, utility_function xml_buffer, utility_function_codeSpace xml_buffer, utility_usage{} xml_buffer, utility_usage{}.codeSpace xml_buffer, utility_connected_city_object xml_buffer, utility_year_of_construction xml_date,
      utility_status xml_char(16), utility_location_quality xml_char(12), utility_elevation_quality xml_char(12), utility_consists_of{}.xlink_href xml_buffer, utility_has_material{}.xlink_href xml_buffer, utility_topo_graph_xlink_href xml_buffer, utility_occupied_hollow_space_xlink_href xml_buffer, citygml_level_of_detail{} xml_buffer, utility_class xml_buffer, utility_class_codeSpace xml_buffer, utility_function_of_line xml_buffer, utility_function_of_line_codeSpace xml_buffer, utility_is_gravity xml_boolean, utility_exterior_width xml_real64, utility_exterior_width_units xml_buffer, utility_exterior_height xml_real64, utility_exterior_height_units xml_buffer, utility_exterior_diameter xml_real64, utility_exterior_diameter_units xml_buffer, utility_interior_diameter xml_real64, utility_interior_diameter_units xml_buffer
AttributeRemover_4
    REMOVE_ATTRS = LENGTH,network_graph_id,OWNER,_left_face,GID,YEAR,MATERIAL,STARTELEV,ENDID,_left_edge,STARTINV,_right_face,ACCURACY,ENDINV,_creation_instance,DIAMETER,network_id,_overlaps,_faces,_right_edge,_direction,ASBUILT,ENDELEV,STARTID
    -> FeatureMerger_8 [SUPPLIER]
    -> FeatureMerger_5 [SUPPLIER]
    -> FeatureMerger_4 [SUPPLIER]
Note: FeatureMerger_5 : Requestor
Note: 9) Exploding list of nodes to show connecting edges
Junction_10
    -> Junction_6
Note: FeatureMerger_5 : Requestor
Note: 10) Filtering and merging processes to determine the type of node based on its connectivity to pipes.
Junction_6
    -> Junction_7
Note: 15) Identifying the Interior Feature Links from the main topology
Note: Junction_10 : Output
Note: 16) Identifying the new Interior Feature Links that appear at intersecting fittings
Junction_7
    -> FeatureMerger_5 [REQUESTOR]
utility_InteriorFeatureLink (writer CITYGML_1)
    attributes: citygml_target_uri xml_buffer, citygml_feature_role xml_buffer, citygml_feature_role_attr_name xml_buffer, citygml_feature_role_attr_val xml_buffer, gml_description xml_buffer, gml_name xml_buffer, utility_direction xml_char(1), utility_link_control xml_xml, utility_start_xlink_href xml_buffer, utility_end_xlink_href xml_buffer
Topology_pipes: Inspector
utility_InterFeatureLink (writer CITYGML_1)
    attributes: citygml_target_uri xml_buffer, citygml_feature_role xml_buffer, citygml_feature_role_attr_name xml_buffer, citygml_feature_role_attr_val xml_buffer, gml_description xml_buffer, gml_name xml_buffer, utility_direction xml_char(1), utility_link_control xml_xml, utility_start_xlink_href xml_buffer, utility_end_xlink_href xml_buffer, utility_type xml_char(8)
utility_Node (writer CITYGML_1)
    attributes: citygml_target_uri xml_buffer, citygml_feature_role xml_buffer, citygml_feature_role_attr_name xml_buffer, citygml_feature_role_attr_val xml_buffer, gml_description xml_buffer, gml_name xml_buffer, utility_type xml_char(8), utility_connection_signature xml_xml, utility_link_control xml_xml
utility_SimpleFunctionalElement (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), utility_medium_supply{}.utility_electrical_medium_supply_utility_potential_supply_utility_supply_utility_flow_rate xml_real64, utility_medium_supply{}.utility_electrical_medium_supply_utility_potential_supply_utility_supply_utility_flow_rate_units xml_buffer, utility_medium_supply{}.utility_electrical_medium_supply_utility_potential_supply_utility_supply_utility_status xml_char(16), utility_medium_supply{}.utility_electrical_medium_supply_utility_current_supply_utility_supply_utility_flow_rate xml_real64, utility_medium_supply{}.utility_electrical_medium_supply_utility_current_supply_utility_supply_utility_flow_rate_units xml_buffer, utility_medium_supply{}.utility_electrical_medium_supply_utility_current_supply_utility_supply_utility_status xml_char(16), utility_medium_supply{}.utility_electrical_medium_supply_utility_storage{}.utility_storage_utility_type xml_buffer, utility_medium_supply{}.utility_electrical_medium_supply_utility_storage{}.utility_storage_utility_type_codeSpace xml_buffer, utility_medium_supply{}.utility_electrical_medium_supply_utility_storage{}.utility_storage_utility_max_capacity xml_real64, utility_medium_supply{}.utility_electrical_medium_supply_utility_storage{}.utility_storage_utility_max_capacity_units xml_buffer, utility_medium_supply{}.utility_electrical_medium_supply_utility_storage{}.utility_storage_utility_fill_level xml_real64, utility_medium_supply{}.utility_electrical_medium_supply_utility_storage{}.utility_storage_utility_inflow_rate xml_real64, utility_medium_supply{}.utility_electrical_medium_supply_utility_storage{}.utility_storage_utility_inflow_rate_units xml_buffer, utility_medium_supply{}.utility_electrical_medium_supply_utility_storage{}.utility_storage_utility_outflow_rate xml_real64, utility_medium_supply{}.utility_electrical_medium_supply_utility_storage{}.utility_storage_utility_outflow_rate_units xml_buffer, utility_medium_supply{}.utility_electrical_medium_supply_utility_type xml_char(29),
      utility_medium_supply{}.utility_gaseous_medium_supply_utility_potential_supply_utility_supply_utility_flow_rate xml_real64, utility_medium_supply{}.utility_gaseous_medium_supply_utility_potential_supply_utility_supply_utility_flow_rate_units xml_buffer, utility_medium_supply{}.utility_gaseous_medium_supply_utility_potential_supply_utility_supply_utility_status xml_char(16), utility_medium_supply{}.utility_gaseous_medium_supply_utility_current_supply_utility_supply_utility_flow_rate xml_real64, utility_medium_supply{}.utility_gaseous_medium_supply_utility_current_supply_utility_supply_utility_flow_rate_units xml_buffer, utility_medium_supply{}.utility_gaseous_medium_supply_utility_current_supply_utility_supply_utility_status xml_char(16), utility_medium_supply{}.utility_gaseous_medium_supply_utility_storage{}.utility_storage_utility_type xml_buffer, utility_medium_supply{}.utility_gaseous_medium_supply_utility_storage{}.utility_storage_utility_type_codeSpace xml_buffer, utility_medium_supply{}.utility_gaseous_medium_supply_utility_storage{}.utility_storage_utility_max_capacity xml_real64, utility_medium_supply{}.utility_gaseous_medium_supply_utility_storage{}.utility_storage_utility_max_capacity_units xml_buffer, utility_medium_supply{}.utility_gaseous_medium_supply_utility_storage{}.utility_storage_utility_fill_level xml_real64, utility_medium_supply{}.utility_gaseous_medium_supply_utility_storage{}.utility_storage_utility_inflow_rate xml_real64, utility_medium_supply{}.utility_gaseous_medium_supply_utility_storage{}.utility_storage_utility_inflow_rate_units xml_buffer, utility_medium_supply{}.utility_gaseous_medium_supply_utility_storage{}.utility_storage_utility_outflow_rate xml_real64, utility_medium_supply{}.utility_gaseous_medium_supply_utility_storage{}.utility_storage_utility_outflow_rate_units xml_buffer, utility_medium_supply{}.utility_gaseous_medium_supply_utility_type xml_buffer, utility_medium_supply{}.utility_gaseous_medium_supply_utility_type_codeSpace xml_buffer, utility_medium_supply{}.utility_liquid_medium_supply_utility_potential_supply_utility_supply_utility_flow_rate xml_real64, utility_medium_supply{}.utility_liquid_medium_supply_utility_potential_supply_utility_supply_utility_flow_rate_units xml_buffer, utility_medium_supply{}.utility_liquid_medium_supply_utility_potential_supply_utility_supply_utility_status xml_char(16), utility_medium_supply{}.utility_liquid_medium_supply_utility_current_supply_utility_supply_utility_flow_rate xml_real64, utility_medium_supply{}.utility_liquid_medium_supply_utility_current_supply_utility_supply_utility_flow_rate_units xml_buffer, utility_medium_supply{}.utility_liquid_medium_supply_utility_current_supply_utility_supply_utility_status xml_char(16), utility_medium_supply{}.utility_liquid_medium_supply_utility_storage{}.utility_storage_utility_type xml_buffer, utility_medium_supply{}.utility_liquid_medium_supply_utility_storage{}.utility_storage_utility_type_codeSpace xml_buffer, utility_medium_supply{}.utility_liquid_medium_supply_utility_storage{}.utility_storage_utility_max_capacity xml_real64, utility_medium_supply{}.utility_liquid_medium_supply_utility_storage{}.utility_storage_utility_max_capacity_units xml_buffer, utility_medium_supply{}.utility_liquid_medium_supply_utility_storage{}.utility_storage_utility_fill_level xml_real64, utility_medium_supply{}.utility_liquid_medium_supply_utility_storage{}.utility_storage_utility_inflow_rate xml_real64, utility_medium_supply{}.utility_liquid_medium_supply_utility_storage{}.utility_storage_utility_inflow_rate_units xml_buffer,
      utility_medium_supply{}.utility_liquid_medium_supply_utility_storage{}.utility_storage_utility_outflow_rate xml_real64, utility_medium_supply{}.utility_liquid_medium_supply_utility_storage{}.utility_storage_utility_outflow_rate_units xml_buffer, utility_medium_supply{}.utility_liquid_medium_supply_utility_type xml_buffer, utility_medium_supply{}.utility_liquid_medium_supply_utility_type_codeSpace xml_buffer, utility_medium_supply{}.utility_optical_medium_supply_utility_potential_supply_utility_supply_utility_flow_rate xml_real64, utility_medium_supply{}.utility_optical_medium_supply_utility_potential_supply_utility_supply_utility_flow_rate_units xml_buffer, utility_medium_supply{}.utility_optical_medium_supply_utility_potential_supply_utility_supply_utility_status xml_char(16), utility_medium_supply{}.utility_optical_medium_supply_utility_current_supply_utility_supply_utility_flow_rate xml_real64, utility_medium_supply{}.utility_optical_medium_supply_utility_current_supply_utility_supply_utility_flow_rate_units xml_buffer, utility_medium_supply{}.utility_optical_medium_supply_utility_current_supply_utility_supply_utility_status xml_char(16), utility_medium_supply{}.utility_optical_medium_supply_utility_storage{}.utility_storage_utility_type xml_buffer, utility_medium_supply{}.utility_optical_medium_supply_utility_storage{}.utility_storage_utility_type_codeSpace xml_buffer, utility_medium_supply{}.utility_optical_medium_supply_utility_storage{}.utility_storage_utility_max_capacity xml_real64, utility_medium_supply{}.utility_optical_medium_supply_utility_storage{}.utility_storage_utility_max_capacity_units xml_buffer, utility_medium_supply{}.utility_optical_medium_supply_utility_storage{}.utility_storage_utility_fill_level xml_real64, utility_medium_supply{}.utility_optical_medium_supply_utility_storage{}.utility_storage_utility_inflow_rate xml_real64, utility_medium_supply{}.utility_optical_medium_supply_utility_storage{}.utility_storage_utility_inflow_rate_units xml_buffer, utility_medium_supply{}.utility_optical_medium_supply_utility_storage{}.utility_storage_utility_outflow_rate xml_real64, utility_medium_supply{}.utility_optical_medium_supply_utility_storage{}.utility_storage_utility_outflow_rate_units xml_buffer, utility_medium_supply{}.utility_optical_medium_supply_utility_type xml_char(7), utility_medium_supply{}.utility_solid_medium_supply_utility_potential_supply_utility_supply_utility_flow_rate xml_real64, utility_medium_supply{}.utility_solid_medium_supply_utility_potential_supply_utility_supply_utility_flow_rate_units xml_buffer, utility_medium_supply{}.utility_solid_medium_supply_utility_potential_supply_utility_supply_utility_status xml_char(16), utility_medium_supply{}.utility_solid_medium_supply_utility_current_supply_utility_supply_utility_flow_rate xml_real64, utility_medium_supply{}.utility_solid_medium_supply_utility_current_supply_utility_supply_utility_flow_rate_units xml_buffer, utility_medium_supply{}.utility_solid_medium_supply_utility_current_supply_utility_supply_utility_status xml_char(16), utility_medium_supply{}.utility_solid_medium_supply_utility_storage{}.utility_storage_utility_type xml_buffer, utility_medium_supply{}.utility_solid_medium_supply_utility_storage{}.utility_storage_utility_type_codeSpace xml_buffer, utility_medium_supply{}.utility_solid_medium_supply_utility_storage{}.utility_storage_utility_max_capacity xml_real64, utility_medium_supply{}.utility_solid_medium_supply_utility_storage{}.utility_storage_utility_max_capacity_units xml_buffer,
      utility_medium_supply{}.utility_solid_medium_supply_utility_storage{}.utility_storage_utility_fill_level xml_real64, utility_medium_supply{}.utility_solid_medium_supply_utility_storage{}.utility_storage_utility_inflow_rate xml_real64, utility_medium_supply{}.utility_solid_medium_supply_utility_storage{}.utility_storage_utility_inflow_rate_units xml_buffer, utility_medium_supply{}.utility_solid_medium_supply_utility_storage{}.utility_storage_utility_outflow_rate xml_real64, utility_medium_supply{}.utility_solid_medium_supply_utility_storage{}.utility_storage_utility_outflow_rate_units xml_buffer, utility_medium_supply{}.utility_solid_medium_supply_utility_type xml_buffer, utility_medium_supply{}.utility_solid_medium_supply_utility_type_codeSpace xml_buffer, utility_medium_supply{}.utility_abstract_medium_supply_utility_potential_supply_utility_supply_utility_flow_rate xml_real64, utility_medium_supply{}.utility_abstract_medium_supply_utility_potential_supply_utility_supply_utility_flow_rate_units xml_buffer, utility_medium_supply{}.utility_abstract_medium_supply_utility_potential_supply_utility_supply_utility_status xml_char(16), utility_medium_supply{}.utility_abstract_medium_supply_utility_current_supply_utility_supply_utility_flow_rate xml_real64, utility_medium_supply{}.utility_abstract_medium_supply_utility_current_supply_utility_supply_utility_flow_rate_units xml_buffer, utility_medium_supply{}.utility_abstract_medium_supply_utility_current_supply_utility_supply_utility_status xml_char(16), utility_medium_supply{}.utility_abstract_medium_supply_utility_storage{}.utility_storage_utility_type xml_buffer, utility_medium_supply{}.utility_abstract_medium_supply_utility_storage{}.utility_storage_utility_type_codeSpace xml_buffer, utility_medium_supply{}.utility_abstract_medium_supply_utility_storage{}.utility_storage_utility_max_capacity xml_real64, utility_medium_supply{}.utility_abstract_medium_supply_utility_storage{}.utility_storage_utility_max_capacity_units xml_buffer, utility_medium_supply{}.utility_abstract_medium_supply_utility_storage{}.utility_storage_utility_fill_level xml_real64, utility_medium_supply{}.utility_abstract_medium_supply_utility_storage{}.utility_storage_utility_inflow_rate xml_real64, utility_medium_supply{}.utility_abstract_medium_supply_utility_storage{}.utility_storage_utility_inflow_rate_units xml_buffer, utility_medium_supply{}.utility_abstract_medium_supply_utility_storage{}.utility_storage_utility_outflow_rate xml_real64, utility_medium_supply{}.utility_abstract_medium_supply_utility_storage{}.utility_storage_utility_outflow_rate_units xml_buffer, utility_role_in_network{}.xlink_href xml_buffer, citygml_appearance{}.xlink_href xml_buffer, utility_function xml_buffer, utility_function_codeSpace xml_buffer, utility_usage{} xml_buffer, utility_usage{}.codeSpace xml_buffer, utility_connected_city_object xml_buffer, utility_year_of_construction xml_date,
      utility_status xml_char(16), utility_location_quality xml_char(12), utility_elevation_quality xml_char(12), utility_consists_of{}.xlink_href xml_buffer, utility_has_material{}.xlink_href xml_buffer, utility_topo_graph_xlink_href xml_buffer, utility_occupied_hollow_space_xlink_href xml_buffer, citygml_level_of_detail{} xml_buffer, utility_class xml_buffer, utility_class_codeSpace xml_buffer
utility_FeatureGraph (writer CITYGML_1)
    attributes: citygml_target_uri xml_buffer, citygml_feature_role xml_buffer, citygml_feature_role_attr_name xml_buffer, citygml_feature_role_attr_val xml_buffer, gml_description xml_buffer, gml_name xml_buffer, utility_link_member{}.xlink_href xml_buffer, utility_node_member{}.xlink_href xml_buffer
3DForcer
    KEEPZVAL = No
    ZVALATTR = @Value(NODEELEV)
    -> Inspector_4
Inspector_4
Appurtenances_subset (reader ESRISHAPE_2)
    attributes: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
Note: Still undecided on the best way to use elevations
Note: 11) / Above: naming EXTERIOR nodes of pipes (4 different types) / Below: naming nodes of appurtenances. Includes the 2 newly identified appuretenance types that were not included in the shapefiles: intersecting fittings and adjoining fittings
GEOTIFF (reader GEOTIFF_1)
    -> Inspector_5
    -> SurfaceDraper_2 [POINTS/LINES]
    -> SurfaceDraper [POINTS/LINES]
Note: 8) Naming Pipes and PipeFeatureGraphs
Inspector

Bookmark: Create new network
Creator_Network
    GEOMTYPE = Geometry Object
    NUM = 1
    CREATED -> UUIDGenerator_NetworkID

Bookmark: Create UUID for network and network graph
UUIDGenerator_NetworkID
    UUID_ATTR = network_id
    -> SC_NetworkID
SC_NetworkID: StringConcatenator
    ACTION = Overwrite Existing Attributes
    ATTRLIST = network_id
    PARM_LINE = fme_basicstring:11%18:NetworkID)_@Value(network_id)
    -> UUIDGenerator_NetworkGraphID
UUIDGenerator_NetworkGraphID
    UUID_ATTR = network_graph_id
    -> SC_NetworkGraphID
SC_NetworkGraphID: StringConcatenator
    ACTION = Overwrite Existing Attributes
    ATTRLIST = network_graph_id
    PARM_LINE = fme_basicstring:16%24:NetworkGraphID)_@Value(network_graph_id)
    -> AttRen_NetworkID
    -> AttRen_NetworkGraphID
    -> UUIDGenerator_LiquidMedium
    -> Junction_2

Bookmark: Network
AttRen_NetworkID: AttributeRenamer
    ATTR_TABLE = RENAME_SET_DEFAULT network_id > gml_id
    -> AttCre_Class_Function_Usage
AttCre_Class_Function_Usage: AttributeCreator
    ATTR_TABLE:
      SET_TO utility_class = Storm_sewer_gravity
      SET_TO utility_function{0} = disposal
      SET_TO utility_usage{0} = disposal
    -> utility_Network (writer CITYGML_1)

Bookmark: NetworkGraph
AttRen_NetworkGraphID: AttributeRenamer
    ATTR_TABLE:
      RENAME_SET_DEFAULT network_id > gml_parent_id
      RENAME_SET_DEFAULT network_graph_id > gml_id
    -> AttCre_FeatureRole
AttCre_FeatureRole: AttributeCreator
    ATTR_TABLE = SET_TO citygml_feature_role = topoGraph
    -> utility_NetworkGraph (writer CITYGML_1)

Bookmark: Create UUID for LiquidMedium
UUIDGenerator_LiquidMedium
    UUID_ATTR = liquid_id
    -> SC_LiquidMediumID
SC_LiquidMediumID: StringConcatenator
    ACTION = Overwrite Existing Attributes
    ATTRLIST = liquid_id
    PARM_LINE = fme_basicstring:16%17:LiquidMediumID)_@Value(liquid_id)
    -> AttRen_LiquidMedium

Bookmark: LiquidMedium
AttRen_LiquidMedium: AttributeRenamer
    ATTR_TABLE:
      RENAME_SET_DEFAULT network_id > gml_parent_id
      RENAME_SET_DEFAULT liquid_id > gml_id
    -> AttCre_FeatureRole_Type_AssociatedNetwork
AttCre_FeatureRole_Type_AssociatedNetwork: AttributeCreator
    ATTR_TABLE:
      SET_TO citygml_feature_role = transportedMedium
      SET_TO utility_type = stormWater
      SET_TO utility_associated_network{0}.xlink_href = #@Value(gml_parent_id)
      SET_TO utility_is_corrosive = false
      SET_TO utility_is_explosive = false
      SET_TO utility_flammable = 0
    -> utility_LiquidMedium (writer CITYGML_1)

Bookmark: Topology of pipes with lines intersecting them outside of nodes
LineOnLineOverlayer
    ATTRS_ACCUM_MODE = Use Attributes From One Feature
    CLEANING_TOLERANCE = Automatic
    DEAGGREGATE_INPUT = Yes
    GENERATE_LIST_DROP = NO
    OV_ATTR = _overlaps
    SEPARATE_COLLINEAR_SEGMENTS = No
    LINE -> AttributeFilter_2
AttributeFilter_2
    ATTR_NAME = TYPE
    ATTR_VALUES = <Empty>,<Missing>,<Null>,<Unfiltered>,Main,Service,Lead,Lead2
    Main -> TopB_MainLines_intersections
AttributeFilter_4
    ATTR_NAME = TYPE
    ATTR_VALUES = <Empty>,<Missing>,<Null>,<Unfiltered>,Main,Service,Lead,Lead2
    Lead -> LineOnLineOverlayer_2 [LINE]
    Lead2 -> LineOnLineOverlayer_2 [LINE]
LineOnLineOverlayer_2
    ATTRS_ACCUM_MODE = Use Attributes From One Feature
    CLEANING_TOLERANCE = Automatic
    DEAGGREGATE_INPUT = Yes
    GENERATE_LIST_DROP = NO
    OV_ATTR = _overlaps
    SEPARATE_COLLINEAR_SEGMENTS = No
    LINE -> AttributeFilter_5
AttributeFilter_5
    ATTR_NAME = TYPE
    ATTR_VALUES = <Empty>,<Missing>,<Null>,<Unfiltered>,Main,Service,Lead,Lead2
    Lead -> TopB_LeadLines_intersections

Bookmark: Topology of segmented hierarchy types
TopB_MainLines_intersections: TopologyBuilder
    ALLOW_CYCLES = No
    BOUNDING_EDGES = All
    DEAGGREGATE_INPUT = Yes
    GENERATION_MODE = ENDS
    LIST_NAME_EDGES = list_edges_mains_internal_nodes
    MAX = 0
    OVERLAPPING_MODE = No
    NODE -> AM_Mains_inter_nodes
    LINE -> AM_main_inter_edges
TopB_LeadLines_intersections: TopologyBuilder
    ALLOW_CYCLES = No
    BOUNDING_EDGES = All
    DEAGGREGATE_INPUT = Yes
    GENERATION_MODE = ENDS
    LIST_NAME_EDGES = list_edges_leads_internal_nodes
    MAX = 0
    OVERLAPPING_MODE = No
    NODE -> AM_Leads_inter_nodes
    LINE -> AM_Leads_inter_edges

Bookmark: Adding some traceability
AM_Mains_inter_nodes: AttributeManager
    ATTR_TABLE = SET_TO _node_number = MainALL#@Value(_node_number)
    -> Main_vs_Main_intersected [Candidate]
AM_main_inter_edges: AttributeManager
    ATTR_TABLE:
      SET_TO _from_node = MainALL#@Value(_from_node)
      SET_TO _to_node = MainALL#@Value(_to_node)
    -> TopB_SegmentedNetwork
AM_Leads_inter_nodes: AttributeManager
    ATTR_TABLE = SET_TO _node_number = LeadALL#@Value(_node_number)
    -> Lead_vs_Lead_intersected [Candidate]
AM_Leads_inter_edges: AttributeManager
    ATTR_TABLE:
      SET_TO _from_node = LeadALL#@Value(_from_node)
      SET_TO _to_node = LeadALL#@Value(_to_node)
    -> TopB_SegmentedNetwork
AM_Mains_nodes: AttributeManager
    ATTR_TABLE = SET_TO _node_number = MainEXTERIOR#@Value(_node_number)
    -> Main_vs_Main_intersected [Filter]
AM_Mains_edges: AttributeManager
    ATTR_TABLE:
      SET_TO _from_node = MainEXTERIOR#@Value(_from_node)
      SET_TO _to_node = MainEXTERIOR#@Value(_to_node)
    -> FM_Main_lines [REQUESTOR]
AM_Service_nodes: AttributeManager
    ATTR_TABLE = SET_TO _node_number = ServiceEXTERIOR#@Value(_node_number)
AM_Service_edges: AttributeManager
    ATTR_TABLE:
      SET_TO _from_node = ServiceEXTERIOR#@Value(_from_node)
      SET_TO _to_node = ServiceEXTERIOR#@Value(_to_node)
    -> TopB_SegmentedNetwork
AM_Leads_nodes: AttributeManager
    ATTR_TABLE = SET_TO _node_number = LeadEXTERIOR#@Value(_node_number)
    -> Lead_vs_Lead_intersected [Filter]
AM_Leads_edges: AttributeManager
    ATTR_TABLE:
      SET_TO _from_node = LeadEXTERIOR#@Value(_from_node)
      SET_TO _to_node = LeadEXTERIOR#@Value(_to_node)
    -> FM_Lead_lines [REQUESTOR]
AM_Leads2_nodes: AttributeManager
    ATTR_TABLE = SET_TO _node_number = Lead2EXTERIOR#@Value(_node_number)
AM_Leads2_edges: AttributeManager
    ATTR_TABLE:
      SET_TO _from_node = Lead2EXTERIOR#@Value(_from_node)
      SET_TO _to_node = Lead2EXTERIOR#@Value(_to_node)
    -> TopB_SegmentedNetwork

Bookmark: Topology of individual hierarchies
TopB_MainLines: TopologyBuilder
    ALLOW_CYCLES = No
    BOUNDING_EDGES = All
    DEAGGREGATE_INPUT = Yes
    GENERATION_MODE = ENDS
    MAX = 0
    OVERLAPPING_MODE = No
    NODE -> AM_Mains_nodes
    LINE -> AM_Mains_edges
TopB_ServiceLines: TopologyBuilder
    ALLOW_CYCLES = No
    BOUNDING_EDGES = All
    DEAGGREGATE_INPUT = Yes
    GENERATION_MODE = ENDS
    LIST_NAME_EDGES = edges_list_service
    MAX = 0
    OVERLAPPING_MODE = No
    NODE -> AM_Service_nodes
    LINE -> AM_Service_edges
TopB_LeadLines: TopologyBuilder
    ALLOW_CYCLES = No
    BOUNDING_EDGES = All
    DEAGGREGATE_INPUT = Yes
    GENERATION_MODE = ENDS
    MAX = 0
    OVERLAPPING_MODE = No
    NODE -> AM_Leads_nodes
    LINE -> AM_Leads_edges
TopB_Lead2Lines: TopologyBuilder
    ALLOW_CYCLES = No
    BOUNDING_EDGES = All
    DEAGGREGATE_INPUT = Yes
    GENERATION_MODE = ENDS
    MAX = 0
    OVERLAPPING_MODE = No
    NODE -> AM_Leads2_nodes
    LINE -> AM_Leads2_edges

Bookmark: Spatial filters for identifying specific nodes
Main_vs_Main_intersected: SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    FAILED -> Fittings_at_continuous_mains [Filter]
Lead_vs_Lead_intersected: SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    FAILED -> Fittings_at_continuous_secondaries [Filter]
AttributeFilter_7
    ATTR_NAME = TYPE
    ATTR_VALUES = <Empty>,<Missing>,<Null>,<Unfiltered>,Main,Service,Lead,Lead2
    Main -> SpatialFilter_2 [Candidate]
    Service -> Fittings_at_continuous_mains [Candidate]
    Lead -> Fittings_at_continuous_mains [Candidate]
    Lead2 -> Fittings_at_continuous_secondaries [Candidate]
Fittings_at_continuous_mains: SpatialFilter
    AGGREGATE_HANDLING = Yes
    BASE_TYPE = Multiple Filters
    CURVE_BOUNDARY_RULE_PARAM = Default Rule
    PASS_CRITERIA = Pass Against One Filter
    PREDATTR = _predicate
    PREDICATES = INTERSECTS
    USE_BOUNDING_BOX = No
    PASSED -> Nodes_of_Fittings_Intersection
    PASSED -> External_nodes_of_connections_at_intersections
    PASSED -> Fittings_between_connecting_pipes [Filter]
    PASSED -> AttributeRenamer_17
    FAILED -> SpatialFilter [Candidate]
Fittings_at_continuous_secondaries: SpatialFilter
    AGGREGATE_HANDLING = Yes
    BASE_TYPE = Multiple Filters
    CURVE_BOUNDARY_RULE_PARAM = Default Rule
    PASS_CRITERIA = Pass Against One Filter
    PREDATTR = _predicate
    PREDICATES = INTERSECTS
    USE_BOUNDING_BOX = No
    PASSED -> Nodes_of_Fittings_Intersection
    PASSED -> External_nodes_of_connections_at_intersections
    PASSED -> Fittings_between_connecting_pipes [Filter]
    PASSED -> AttributeRenamer_17
    FAILED -> SpatialFilter [Candidate]
AttributeRenamer_17
    ATTR_TABLE:
      RENAME_SET_DEFAULT PIPEID > connection_PIPEID
      RENAME_SET_DEFAULT TYPE > connection_TYPE
    -> FeatureMerger_6 [REQUESTOR]
    -> FeatureMerger_7 [SUPPLIER]
FeatureMerger_7
    ATTR_ACCUM_MODE = Merge Supplier
    ATTR_CONFLICT_RES = Use Requestor
    IGNORE_NULLS = No
    JOIN_KEYS = @Value(_node_number) @Value(_node_number) AUTO @Value(PIPEID) @Value(connection_PIPEID) AUTO
    MERGE_TYPE = Attributes Only
    PROCESS_DUPS = NO
    REJECT_NULL_MISSING_KEYS = No
    SUPPLIERS_FIRST = No
    UNMERGED_REQUESTOR -> FeatureMerger_6 [SUPPLIER]
FeatureMerger_6
    ATTR_ACCUM_MODE = Merge Supplier
    ATTR_CONFLICT_RES = Use Supplier
    IGNORE_NULLS = No
    JOIN_KEYS = @Value(_node_number) @Value(_node_number) AUTO
    MERGE_TYPE = Attributes Only
    PROCESS_DUPS = NO
    REJECT_NULL_MISSING_KEYS = No
    SUPPLIERS_FIRST = No
    MERGED -> New_external_nodes_of_continuous_pipes
Note: LIST: For keeping the information about adjoining pipes
FeatureMerger_3
    ATTR_ACCUM_MODE = Merge Supplier
    ATTR_CONFLICT_RES = Use Requestor
    IGNORE_NULLS = No
    JOIN_KEYS = @Value(_node_number) @Value(_node_number) AUTO
    LIST_ATTRS_TO_INCLUDE = fme_arc_id PIPEID TYPE
    LIST_NAME = list_before_duplicate
    MERGE_TYPE = Attributes Only
    PROCESS_DUPS = NO
    REJECT_NULL_MISSING_KEYS = No
    SUPPLIERS_FIRST = No
    MERGED -> DuplicateFilter_3
DuplicateFilter_3
    INPUT_ORDERED_CHOICE = No
    KEYATTR = _node_number
    DUPLICATE -> Fittings_between_connecting_pipes [Candidate]
Fittings_between_connecting_pipes: SpatialFilter
    AGGREGATE_HANDLING = Yes
    BASE_TYPE = Multiple Filters
    CURVE_BOUNDARY_RULE_PARAM = Default Rule
    PASS_CRITERIA = Pass Against One Filter
    PREDATTR = _predicate
    PREDICATES = INTERSECTS
    USE_BOUNDING_BOX = No
    FAILED -> Nodes_of_Fittings_Adjacent
NeighborFinder
    ATTR_ACCUM_MODE = Merge Candidate
    ATTR_CONFLICT_RES = Use Base
    CANDIDATES_FIRST = No
    INSERT_VERTEX = No
    K = 1
    MEASURES_FROM_CANDIDATE = Yes
    MEASURE_TYPE = Continuous
    MODE = Bases and Candidates
    TREAT_POLYGON_AS = Lines
    MATCHED -> AttributeRemover_3
AttributeRemover_3
    REMOVE_ATTRS = _closest_base_x,LENGTH,_distance,_left_face,MATERIAL,_closest_candidate_x,STARTELEV,_closest_base_y,ENDID,_candidate_angle,_left_edge,_candidate_label_angle,_to_node,STARTINV,ENDINV,_right_face,_from_node,DIAMETER,_closest_candidate_y,_overlaps,_faces,_right_edge,ENDELEV,_angle,_edge_id,STARTID
    -> Node_appurtenances

Bookmark: Topology of segmented network. Missing additional interior feature links!!!
Note: LIST: Edges connected to the nodes
TopB_SegmentedNetwork: TopologyBuilder
    ALLOW_CYCLES = No
    BOUNDING_EDGES = All
    DEAGGREGATE_INPUT = Yes
    GENERATION_MODE = ENDS
    LIST_NAME_EDGES = edges_list_main_topology
    MAX = 0
    OVERLAPPING_MODE = No
    NODE -> AttributeRemover_2
    NODE -> NeighborFinder [CANDIDATE]
    NODE -> Topology_nodes
    NODE -> Junction_3
    LINE -> NetworkFlowOrientor [LINE]
NetworkFlowOrientor
    DIRECTION_ATTR = _direction
    NETWORK -> Junction_10
    NETWORK -> Topology_pipes
    NETWORK -> AF_service_and_lead2_lines
    NETWORK -> FM_Main_lines [SUPPLIER]
    NETWORK -> FM_Lead_lines [SUPPLIER]

Bookmark: Exploding list to obtain individual nodes
AttributeRemover_2
    REMOVE_ATTRS = YEAR,MATERIAL,_edge_id,_faces,DIAMETER,ENDINV,STARTID,_to_node,_from_node,GID,_right_edge,ACCURACY,OWNER,ENDELEV,STARTINV,ASBUILT,_left_face,ENDID,_left_edge,_overlaps,LENGTH,_creation_instance,STARTELEV,_right_face
    -> ListExploder_2
ListExploder_2
    ATTR_ACCUM_MODE = Merge List Attributes
    ATTR_CONFLICT_RES = Use List Attribute Values
    INDEX_ATTR = _element_index
    LIST_ATTR = edges_list_main_topology{}
    ELEMENTS -> ExpressionEvaluator
ExpressionEvaluator
    ACTION = Overwrite Existing Attributes
    ATTRLIST = fme_arc_id
    EXPRESSION = @abs(@Value(fme_arc_id))
    -> AttributeFilter_7
    -> FeatureMerger_3 [REQUESTOR]
    -> FeatureMerger_3 [SUPPLIER]
    -> FeatureMerger_7 [REQUESTOR]

Bookmark: External nodes of continuous pipes at fittings
New_external_nodes_of_continuous_pipes: UUIDGenerator
    UUID_ATTR = node_pipe_continuous_exterior_intersection_id
    -> StrCon_8
StrCon_8: StringConcatenator
    ACTION = Overwrite Existing Attributes
    ATTRLIST = node_pipe_continuous_exterior_intersection_id
    PARM_LINE = fme_basicstring:41%53:NodePipeContinuousExteriorIntersectionID_@Value(node_pipe_continuous_exterior_intersection_id)
    -> External_nodes_of_continuous_pipes_at_intersections---Intersection_Fittings [REQUESTOR]
    -> SpatialFilter_2 [Filter]
    -> FeatureMerger [REQUESTOR]
    -> FeatureMerger_2 [SUPPLIER]
    -> AttributeRenamer_14

Bookmark: External nodes of continuous pipes at appurtenances
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    FAILED -> External_nodes_of_continuous_pipes
External_nodes_of_continuous_pipes: UUIDGenerator
    UUID_ATTR = node_pipe_continuous_exterior_appurtenance_id
    -> StrCon_9
StrCon_9: StringConcatenator
    ACTION = Overwrite Existing Attributes
    ATTRLIST = node_pipe_continuous_exterior_appurtenance_id
    PARM_LINE = fme_basicstring:41%53:NodePipeContinuousExteriorAppurtenanceID_@Value(node_pipe_continuous_exterior_appurtenance_id)
    -> External_nodes_of_continuous_pipes_at_ends---Appurtenances [REQUESTOR]
    -> AttributeRenamer_13
    -> AttributeRenamer_4

Bookmark: Identifying the InteriorFeatureLinks of the pipes from the main topological step (this does not include the additional internal pipes at the 'intersecting' type fittings)
AttributeRenamer_4
    ATTR_TABLE = RENAME_SET_DEFAULT node_pipe_continuous_exterior_appurtenance_id > node_id
    -> Junction
AttributeRenamer_27
    ATTR_TABLE = RENAME_SET_DEFAULT node_pipe_connecting_exterior_intersection_id > node_id
    -> Junction
AttributeRenamer_26
    ATTR_TABLE = RENAME_SET_DEFAULT node_pipe_connecting_exterior_other_id > node_id
    -> Junction
AttributeRenamer_5
    ATTR_TABLE = RENAME_SET_DEFAULT node_pipe_continuous_interior_id > node_id
    -> Junction
Junction
    -> FeatureMerger_9 [SUPPLIER]
    -> FeatureMerger_10 [SUPPLIER]
FeatureMerger_5
    ATTR_ACCUM_MODE = Merge Supplier
    ATTR_CONFLICT_RES = Use Requestor
    IGNORE_NULLS = No
    JOIN_KEYS = @Value(PIPEID) @Value(PIPEID) AUTO
    MERGE_TYPE = Attributes Only
    PROCESS_DUPS = NO
    REJECT_NULL_MISSING_KEYS = No
    SUPPLIERS_FIRST = No
    MERGED -> FeatureMerger_9 [REQUESTOR]
FeatureMerger_9
    ATTR_ACCUM_MODE = Merge Supplier
    ATTR_CONFLICT_RES = Use Requestor
    IGNORE_NULLS = No
    JOIN_KEYS = @Value(PIPEID) @Value(PIPEID) AUTO @Value(_from_node) @Value(_node_number) AUTO
    MERGE_TYPE = Attributes Only
    PROCESS_DUPS = NO
    REJECT_NULL_MISSING_KEYS = No
    SUPPLIERS_FIRST = No
    MERGED -> AttributeRenamer_2
AttributeRenamer_2
    ATTR_TABLE = RENAME_SET_DEFAULT node_id > utility_start_xlink_href
    -> FeatureMerger_10 [REQUESTOR]
FeatureMerger_10
    ATTR_ACCUM_MODE = Merge Supplier
    ATTR_CONFLICT_RES = Use Requestor
    IGNORE_NULLS = No
    JOIN_KEYS = @Value(PIPEID) @Value(PIPEID) AUTO @Value(_to_node) @Value(_node_number) AUTO
    MERGE_TYPE = Attributes Only
    PROCESS_DUPS = NO
    REJECT_NULL_MISSING_KEYS = No
    SUPPLIERS_FIRST = No
    MERGED -> AttributeRenamer_3
AttributeRenamer_3
    ATTR_TABLE = RENAME_SET_DEFAULT node_id > utility_end_xlink_href
    -> UUIDGenerator_InteriorFeatureLinkID

Bookmark: Adding the Pipe Feature Graph information to the nodes (belonging to the pipe)
AttributeRenamer_13
    ATTR_TABLE = RENAME_SET_DEFAULT node_pipe_continuous_exterior_appurtenance_id > node_id
    -> FeatureMerger_4 [REQUESTOR]
AttributeRenamer_14
    ATTR_TABLE = RENAME_SET_DEFAULT node_pipe_continuous_exterior_intersection_id > node_id
    -> FeatureMerger_4 [REQUESTOR]
AttributeRenamer_15
    ATTR_TABLE = RENAME_SET_DEFAULT node_pipe_connecting_exterior_intersection_id > node_id
    -> FeatureMerger_4 [REQUESTOR]
AttributeRenamer_16
    ATTR_TABLE = RENAME_SET_DEFAULT node_pipe_connecting_exterior_other_id > node_id
    -> FeatureMerger_4 [REQUESTOR]
FeatureMerger_4
    ATTR_ACCUM_MODE = Merge Supplier
    ATTR_CONFLICT_RES = Use Requestor
    IGNORE_NULLS = No
    JOIN_KEYS = @Value(PIPEID) @Value(PIPEID) AUTO
    MERGE_TYPE = Attributes Only
    PROCESS_DUPS = NO
    REJECT_NULL_MISSING_KEYS = No
    SUPPLIERS_FIRST = No
    MERGED -> AttributeCreator_5

Bookmark: Identifying the Interior nodes of continuous pipes (at intersecting fittings)
Note: LIST: linking to the nodes from the main topology the exterior nodes at intersections
FeatureMerger_2
    ATTR_ACCUM_MODE = Merge Supplier
    ATTR_CONFLICT_RES = Use Supplier
    IGNORE_NULLS = No
    JOIN_KEYS = @Value(_node_number) @Value(_node_number) AUTO
    LIST_ATTRS_TO_INCLUDE = PIPEID TYPE connection_PIPEID connection_TYPE
    LIST_NAME = node_internal
    MERGE_TYPE = Attributes Only
    PROCESS_DUPS = NO
    REJECT_NULL_MISSING_KEYS = No
    SUPPLIERS_FIRST = No
    MERGED -> FeatureMerger_8 [REQUESTOR]
FeatureMerger_8
    ATTR_ACCUM_MODE = Merge Supplier
    ATTR_CONFLICT_RES = Use Requestor
    IGNORE_NULLS = No
    JOIN_KEYS = @Value(PIPEID) @Value(PIPEID) AUTO
    MERGE_TYPE = Attributes Only
    PROCESS_DUPS = NO
    REJECT_NULL_MISSING_KEYS = No
    SUPPLIERS_FIRST = No
    MERGED -> New_internal_nodes_of_continuous_pipes_2

Bookmark: External nodes of connecting pipes at fittings with continuous pipes
External_nodes_of_connections_at_intersections: UUIDGenerator
    UUID_ATTR = node_pipe_connecting_exterior_intersection_id
    -> StrCon_7
StrCon_7: StringConcatenator
    ACTION = Overwrite Existing Attributes
    ATTRLIST = node_pipe_connecting_exterior_intersection_id
    PARM_LINE = fme_basicstring:41%53:NodePipeConnectionExteriorIntersectionID_@Value(node_pipe_connecting_exterior_intersection_id)
    -> External_nodes_of_connecting_pipes_at_intersections---Intersection_Fittings [SUPPLIER]
    -> SpatialFilter [Filter]
    -> AttributeRenamer_27
    -> AttributeRenamer_15

Bookmark: Nodes of fittings connecting intersecting pipes
Nodes_of_Fittings_Intersection: UUIDGenerator
    UUID_ATTR = node_fitting_intersection_id
    -> StrCon
StrCon: StringConcatenator
    ACTION = Overwrite Existing Attributes
    ATTRLIST = node_fitting_intersection_id
    PARM_LINE = fme_basicstring:26%36:NodeFittingIntersectionID_@Value(node_fitting_intersection_id)
    -> AttributeCreator_7
AttributeCreator_7
    ATTR_TABLE = SET_TO type_of_appurtenance = fitting_intersection
    -> SpatialFilter [Filter]
    -> External_nodes_of_connecting_pipes_at_intersections---Intersection_Fittings [REQUESTOR]
    -> UUIDGenerator_AppurtenanceID
    -> External_nodes_of_continuous_pipes_at_intersections---Intersection_Fittings [SUPPLIER]

Bookmark: External nodes of connecting pipes (which are not at fittings continuous pipes)
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    FAILED -> External_nodes_of_connections_the_other_one
External_nodes_of_connections_the_other_one: UUIDGenerator
    UUID_ATTR = node_pipe_connecting_exterior_other_id
    -> StrCon_6
StrCon_6: StringConcatenator
    ACTION = Overwrite Existing Attributes
    ATTRLIST = node_pipe_connecting_exterior_other_id
    PARM_LINE = fme_basicstring:34%46:NodePipeConnectingExteriorOtherID_@Value(node_pipe_connecting_exterior_other_id)
    -> External_nodes_of_connecting_pipes_at_ends---Adjoining_fittings [REQUESTOR]
    -> AttributeRenamer_26
    -> AttributeRenamer_16
    -> External_nodes_of_connecting_pipes_at_ends---Appurtenances [REQUESTOR]

Bookmark: Comparing all external nodes to create inter feature links of different types
External_nodes_of_continuous_pipes_at_intersections---Intersection_Fittings: FeatureMerger
    ATTR_ACCUM_MODE = Merge Supplier
    ATTR_CONFLICT_RES = Use Requestor
    IGNORE_NULLS = No
    JOIN_KEYS = @Value(_node_number) @Value(_node_number) AUTO
    MERGE_TYPE = Attributes Only
    PROCESS_DUPS = NO
    REJECT_NULL_MISSING_KEYS = No
    SUPPLIERS_FIRST = No
    MERGED -> AttributeRenamer_6
AttributeRenamer_6
    ATTR_TABLE:
      RENAME_SET_DEFAULT node_fitting_intersection_id > utility_start_xlink_href
      RENAME_SET_DEFAULT node_pipe_continuous_exterior_intersection_id > utility_end_xlink_href
    -> UUIDGenerator_InterFeatureLink__fake__2
External_nodes_of_connecting_pipes_at_intersections---Intersection_Fittings: FeatureMerger
    ATTR_ACCUM_MODE = Merge Supplier
    ATTR_CONFLICT_RES = Use Requestor
    IGNORE_NULLS = No
    JOIN_KEYS = @Value(_node_number) @Value(_node_number) AUTO @Value(PIPEID) @Value(PIPEID) AUTO
    MERGE_TYPE = Attributes Only
    PROCESS_DUPS = NO
    REJECT_NULL_MISSING_KEYS = No
    SUPPLIERS_FIRST = No
    MERGED -> AttributeRenamer_7
AttributeRenamer_7
    ATTR_TABLE:
      RENAME_SET_DEFAULT node_fitting_intersection_id > utility_start_xlink_href
      RENAME_SET_DEFAULT node_pipe_connecting_exterior_intersection_id > utility_end_xlink_href
    -> UUIDGenerator_InterFeatureLink__fake__2
External_nodes_of_connecting_pipes_at_ends---Adjoining_fittings: FeatureMerger
    ATTR_ACCUM_MODE = Merge Supplier
    ATTR_CONFLICT_RES = Use Requestor
    IGNORE_NULLS = No
    JOIN_KEYS = @Value(_node_number) @Value(_node_number) AUTO @Value(PIPEID) @Value(PIPEID) AUTO
    MERGE_TYPE = Attributes Only
    PROCESS_DUPS = NO
    REJECT_NULL_MISSING_KEYS = No
    SUPPLIERS_FIRST = No
    MERGED -> AttributeRenamer_10
AttributeRenamer_10
    ATTR_TABLE:
      RENAME_SET_DEFAULT node_fitting_adjacent_id > utility_start_xlink_href
      RENAME_SET_DEFAULT node_pipe_connecting_exterior_other_id > utility_end_xlink_href
    -> UUIDGenerator_InterFeatureLink__fake__2
External_nodes_of_continuous_pipes_at_ends---Appurtenances: FeatureMerger
    ATTR_ACCUM_MODE = Merge Supplier
    ATTR_CONFLICT_RES = Use Requestor
    IGNORE_NULLS = No
    JOIN_KEYS = @Value(_node_number) @Value(_node_number) AUTO @Value(PIPEID) @Value(PIPEID) AUTO
    MERGE_TYPE = Attributes Only
    PROCESS_DUPS = NO
    REJECT_NULL_MISSING_KEYS = No
    SUPPLIERS_FIRST = No
    MERGED -> AttributeRenamer_8
AttributeRenamer_8
    ATTR_TABLE:
      RENAME_SET_DEFAULT node_appurtenance_id > utility_start_xlink_href
      RENAME_SET_DEFAULT node_pipe_continuous_exterior_appurtenance_id > utility_end_xlink_href
    -> UUIDGenerator_InterFeatureLink__fake__2
External_nodes_of_connecting_pipes_at_ends---Appurtenances: FeatureMerger
    ATTR_ACCUM_MODE = Merge Supplier
    ATTR_CONFLICT_RES = Use Requestor
    IGNORE_NULLS = No
    JOIN_KEYS = @Value(_node_number) @Value(_node_number) AUTO @Value(PIPEID) @Value(PIPEID) AUTO
    MERGE_TYPE = Attributes Only
    PROCESS_DUPS = NO
    REJECT_NULL_MISSING_KEYS = No
    SUPPLIERS_FIRST = No
    MERGED -> AttributeRenamer_9
AttributeRenamer_9
    ATTR_TABLE:
      RENAME_SET_DEFAULT node_appurtenance_id > utility_start_xlink_href
      RENAME_SET_DEFAULT node_pipe_connecting_exterior_other_id > utility_end_xlink_href
    -> UUIDGenerator_InterFeatureLink__fake__2

Bookmark: Nodes of fittings connecting adjacent pipes
Nodes_of_Fittings_Adjacent: UUIDGenerator
    UUID_ATTR = node_fitting_adjacent_id
    -> StrCon_2
StrCon_2: StringConcatenator
    ACTION = Overwrite Existing Attributes
    ATTRLIST = node_fitting_adjacent_id
    PARM_LINE = fme_basicstring:22%32:NodeFittingAdjacentID_@Value(node_fitting_adjacent_id)
    -> AttributeCreator_8
AttributeCreator_8
    ATTR_TABLE = SET_TO type_of_appurtenance = fitting_adjacent
    -> ListExploder_4
    -> UUIDGenerator_AppurtenanceID

Bookmark: Nodes of all appurtenances, including existing ones plus the new fittings which were created (IDs)
ListExploder_4
    ATTR_ACCUM_MODE = Merge List Attributes
    ATTR_CONFLICT_RES = Use List Attribute Values
    INDEX_ATTR = _element_index
    LIST_ATTR = list_before_duplicate{}
    ELEMENTS -> External_nodes_of_connecting_pipes_at_ends---Adjoining_fittings [SUPPLIER]
ListExploder
    ATTR_ACCUM_MODE = Merge List Attributes
    ATTR_CONFLICT_RES = Use List Attribute Values
    INDEX_ATTR = _element_index
    LIST_ATTR = edges_list_main_topology{}
    ELEMENTS -> External_nodes_of_connecting_pipes_at_ends---Appurtenances [SUPPLIER]
    ELEMENTS -> External_nodes_of_continuous_pipes_at_ends---Appurtenances [SUPPLIER]

Bookmark: Selection of lines that will become pipes and pipe feature graphs
FM_Main_lines: FeatureMerger
    ATTR_ACCUM_MODE = Merge Supplier
    ATTR_CONFLICT_RES = Use Supplier
    IGNORE_NULLS = No
    JOIN_KEYS = @Value(PIPEID) @Value(PIPEID) AUTO
    MERGE_TYPE = Attributes Only
    PROCESS_DUPS = NO
    REJECT_NULL_MISSING_KEYS = No
    SUPPLIERS_FIRST = No
    MERGED -> UUIDGenerator_PipeID
    MERGED -> TestFilter
    MERGED -> SurfaceDraper_2 [DRAPE_FEATURES]
AF_service_and_lead2_lines: AttributeFilter
    ATTR_NAME = TYPE
    ATTR_VALUES = <Empty>,<Missing>,<Null>,<Unfiltered>,Main,Lead
    <UNFILTERED> -> UUIDGenerator_PipeID
    <UNFILTERED> -> TestFilter
    <UNFILTERED> -> SurfaceDraper_2 [DRAPE_FEATURES]
FM_Lead_lines: FeatureMerger
    ATTR_ACCUM_MODE = Merge Supplier
    ATTR_CONFLICT_RES = Use Supplier
    IGNORE_NULLS = No
    JOIN_KEYS = @Value(PIPEID) @Value(PIPEID) AUTO
    MERGE_TYPE = Attributes Only
    PROCESS_DUPS = NO
    REJECT_NULL_MISSING_KEYS = No
    SUPPLIERS_FIRST = No
    MERGED -> UUIDGenerator_PipeID
    MERGED -> TestFilter
    MERGED -> SurfaceDraper_2 [DRAPE_FEATURES]

Bookmark: Alternative 2
TestFilter
    DEFAULT_VALUE = All elevations are set
    TEST_LIST:
      "BOOL_OP,AND,COMPOSITE_TEST,""""""1 AND 2"""""",TEST_CLAUSE,TEST @Value(STARTINV) = 0
      TEST @Value(ENDINV) = 0",All elevations at 0,"BOOL_OP,OR,COMPOSITE_TEST,""""""1"""""",TEST_CLAUSE,TEST @Value(STARTINV) = 0",Start elevation 0,"BOOL_OP,OR,COMPOSITE_TEST,""""""1"""""",TEST_CLAUSE,TEST @Value(ENDINV) = 0",End elevation 0
    All elevations at 0 -> SurfaceDraper [DRAPE_FEATURES]
    End elevation 0 -> LengthCalculator
    All elevations are set -> 3DInterpolator
LengthCalculator
    DIM = 2
    LEN_ATTR = length_calculated
    MULT = 1
    -> AttributeManager
AttributeManager
    ATTR_TABLE = SET_TO ENDINV = @Evaluate(@Value(STARTINV)-0.03*@Value(length_calculated))
    -> 3DInterpolator
3DInterpolator
    ZENDATTR = @Value(ENDINV)
    ZSTARTATTR = @Value(STARTINV)
    -> Inspector
Inspector_5
SurfaceDraper
    ADDZ_TYPE = Replace Z
    DRAPE_TYPE = VERTEX
    INTERPOLATION_TYPE = AUTO
    TOLERANCE = 0
    DRAPED_FEATURES -> Offsetter
Offsetter
    MODE = Cartesian Coordinate
    XOFF = 0
    YOFF = 0
    ZOFF = -1.2
    OFFSET -> Inspector

Bookmark: Pipe ID and Pipe Feature Graph ID
UUIDGenerator_PipeID
    UUID_ATTR = pipe_ID
    -> StrCon_11
StrCon_11: StringConcatenator
    ACTION = Overwrite Existing Attributes
    ATTRLIST = pipe_ID
    PARM_LINE = fme_basicstring:7%15:PipeID_@Value(pipe_ID)
    -> UUIDGenerator_PipeFeatureGraphID
UUIDGenerator_PipeFeatureGraphID
    UUID_ATTR = pipe_feature_graph_ID
    -> StrCon_10
StrCon_10: StringConcatenator
    ACTION = Overwrite Existing Attributes
    ATTRLIST = pipe_feature_graph_ID
    PARM_LINE = fme_basicstring:19%29:PipeFeatureGraphID_@Value(pipe_feature_graph_ID)
    -> AttributeRemover_4
    -> GeometryRemover_Pipe_FeatureGraph
    -> DuplicateFilter
    -> Junction_4
Note: FeatureMerger_Material : Requestor
Junction_4
    -> Junction_5

Bookmark: Pipe Feature Graphs
GeometryRemover_Pipe_FeatureGraph
    -> AttributeRenamer_Pioe_FeatureGraphIDs
AttributeRenamer_Pioe_FeatureGraphIDs
    ATTR_TABLE:
      RENAME_SET_DEFAULT pipe_feature_graph_ID > gml_id
      RENAME_SET_DEFAULT network_graph_id > gml_parent_id
    -> AC_Pipe_FeatureGraph_FeatureRole
AC_Pipe_FeatureGraph_FeatureRole: AttributeCreator
    ATTR_TABLE = SET_TO citygml_feature_role = featureGraphMember
    -> utility_FeatureGraph (writer CITYGML_1)

Bookmark: Create UUID for Material
UUIDGenerator_MaterialID
    UUID_ATTR = material_id
    -> StringConcatenator_ExteriorMaterialID
StringConcatenator_ExteriorMaterialID
    ACTION = Overwrite Existing Attributes
    ATTRLIST = material_id
    PARM_LINE = fme_basicstring:10%19:MterialID_@Value(material_id)
    -> FeatureMerger_Material [SUPPLIER]
    -> GeometryRemover

Bookmark: Material
GeometryRemover
    -> AttributeValueMapper_Material
AttributeValueMapper_Material
    DEFAULT_VALUE = unknown
    DIRECTION = Forward (Source To Destination)
    LUT = CP,concrete,PVC,PVC,PE,PE,PERF,PE,UN,unknown
    SRC = MATERIAL
    VAL_ATTR = _looked_up
    -> AttributeRenamer_MaterialID
AttributeRenamer_MaterialID
    ATTR_TABLE = RENAME_SET_DEFAULT material_id > gml_id
    -> AttributeCreator_UtilityType
AttributeCreator_UtilityType
    ATTR_TABLE = SET_TO utility_type = @Value(_looked_up)
    -> utility_ExteriorMaterial (writer CITYGML_1)

Bookmark: Pipes
AttributeCreator
    ATTR_TABLE:
      SET_TO citygml_feature_role = component
      SET_TO citygml_lod_name = lod1Geometry
    -> GeometryPropertySetter_Pipes
GeometryPropertySetter_Pipes
    OVERWRITE_CHOICE = Yes
    REMOVE_ATTRIBUTE = No
    SETTYPE_PARAM = Traits From Attributes
    SRC_ATTRS = citygml_lod_name
    SET -> AttributeRenamer
AttributeRenamer
    ATTR_TABLE:
      RENAME_SET_DEFAULT network_id > gml_parent_id
      RENAME_SET_DEFAULT pipe_ID > gml_id
      RENAME_SET_DEFAULT pipe_feature_graph_ID > feature_graph_id
      RENAME_SET_DEFAULT DIAMETER > utility_interior_diameter
    -> AttributeCreator_2
AttributeCreator_2
    ATTR_TABLE:
      SET_TO utility_topo_graph_xlink_href = @Value(feature_graph_id)
      SET_TO gml_description = @Value(PIPEID)
      SET_TO utility_has_material{0}.xlink_href = @Value(material_id)
      SET_TO utility_class = @Value(TYPE)
    -> utility_RoundPipe (writer CITYGML_1)

Bookmark: Interior nodes of continuous pipes at intersecting fittings (ID)
New_internal_nodes_of_continuous_pipes_2: UUIDGenerator
    UUID_ATTR = node_pipe_continuous_interior_id
    -> StringConcatenator_8
StringConcatenator_8
    ACTION = Overwrite Existing Attributes
    ATTRLIST = node_pipe_continuous_interior_id
    PARM_LINE = fme_basicstring:29%40:NodePipeContinuousInteriorID_@Value(node_pipe_continuous_interior_id)
    -> AttributeRenamer_18
    -> ListExploder_3
    -> AttributeRenamer_5

Bookmark: Identifying the InteriorFeatureLinks of continuos pipes (at 'intersecting' type fitting)
ListExploder_3
    ATTR_ACCUM_MODE = Merge List Attributes
    ATTR_CONFLICT_RES = Use List Attribute Values
    INDEX_ATTR = _element_index
    LIST_ATTR = node_internal{}
    ELEMENTS -> FeatureMerger [SUPPLIER]
FeatureMerger
    ATTR_ACCUM_MODE = Merge Supplier
    ATTR_CONFLICT_RES = Use Requestor
    IGNORE_NULLS = No
    JOIN_KEYS = @Value(connection_PIPEID) @Value(connection_PIPEID) AUTO @Value(_node_number) @Value(_node_number) AUTO
    MERGE_TYPE = Attributes Only
    PROCESS_DUPS = NO
    REJECT_NULL_MISSING_KEYS = No
    SUPPLIERS_FIRST = No
    MERGED -> AttributeRenamer_28
AttributeRenamer_28
    ATTR_TABLE:
      RENAME_SET_DEFAULT node_pipe_continuous_exterior_intersection_id > utility_start_xlink_href
      RENAME_SET_DEFAULT node_pipe_continuous_interior_id > utility_end_xlink_href
    -> UUIDGenerator_InteriorFeatureLinkID

Bookmark: Nodes of pipes - interior
AttributeRenamer_18
    ATTR_TABLE = RENAME_SET_DEFAULT node_pipe_continuous_interior_id > node_id
    -> AttributeCreator_6
AttributeCreator_6
    ATTR_TABLE:
      SET_TO citygml_lod_name = realization
      SET_TO citygml_feature_role = nodeMember
      SET_TO utility_type = interior
    -> AttributeRenamer_19
AttributeRenamer_19
    ATTR_TABLE:
      RENAME_SET_DEFAULT node_id > gml_id
      RENAME_SET_DEFAULT pipe_feature_graph_ID > gml_parent_id
    -> GeometryPropertySetter_3
GeometryPropertySetter_3
    OVERWRITE_CHOICE = Yes
    REMOVE_ATTRIBUTE = No
    SETTYPE_PARAM = Traits From Attributes
    SRC_ATTRS = citygml_lod_name
    SET -> utility_Node (writer CITYGML_1)

Bookmark: Nodes of pipes - Exterior
AttributeCreator_5
    ATTR_TABLE:
      SET_TO citygml_lod_name = realization
      SET_TO citygml_feature_role = nodeMember
      SET_TO utility_type = exterior
    -> AttributeRenamer_12
AttributeRenamer_12
    ATTR_TABLE:
      RENAME_SET_DEFAULT node_id > gml_id
      RENAME_SET_DEFAULT pipe_feature_graph_ID > gml_parent_id
    -> GeometryPropertySetter_2
GeometryPropertySetter_2
    OVERWRITE_CHOICE = Yes
    REMOVE_ATTRIBUTE = No
    SETTYPE_PARAM = Traits From Attributes
    SRC_ATTRS = citygml_lod_name
    SET -> utility_Node (writer CITYGML_1)

Bookmark: Interior Feature Link ID
UUIDGenerator_InteriorFeatureLinkID
    UUID_ATTR = interior_feature_link_id
    -> StrCon_12
StrCon_12: StringConcatenator
    ACTION = Overwrite Existing Attributes
    ATTRLIST = interior_feature_link_id
    PARM_LINE = fme_basicstring:22%32:InteriorFeatureLinkID_@Value(interior_feature_link_id)
    -> AttributeRenamer_InteriorFeatureLinkIDs

Bookmark: Interior Feature Links
AttributeRenamer_InteriorFeatureLinkIDs
    ATTR_TABLE:
      RENAME_SET_DEFAULT interior_feature_link_id > gml_id
      RENAME_SET_DEFAULT pipe_feature_graph_ID > gml_parent_id
    -> AC_InteriorFeatureLink_FeatureRole
AC_InteriorFeatureLink_FeatureRole: AttributeCreator
    ATTR_TABLE:
      SET_TO citygml_feature_role = linkMember
      SET_TO citygml_lod_name = realization
    -> GeometryPropertySetter
GeometryPropertySetter
    OVERWRITE_CHOICE = Yes
    REMOVE_ATTRIBUTE = No
    SETTYPE_PARAM = Traits From Attributes
    SRC_ATTRS = citygml_lod_name
    SET -> utility_InteriorFeatureLink (writer CITYGML_1)

Bookmark: Nodes of existing appurtenances
Node_appurtenances: UUIDGenerator
    UUID_ATTR = node_appurtenance_id
    -> StrCon_3
StrCon_3: StringConcatenator
    ACTION = Overwrite Existing Attributes
    ATTRLIST = node_appurtenance_id
    PARM_LINE = fme_basicstring:19%28:NodeAppurtenanceID_@Value(node_appurtenance_id)
    -> AttributeRenamer_21
AttributeRenamer_21
    ATTR_TABLE = RENAME_SET_DEFAULT TYPE > type_of_appurtenance
    -> UUIDGenerator_AppurtenanceID
    -> ListExploder

Bookmark: Inter Feature Link ID
UUIDGenerator_InterFeatureLink__fake__2
    UUID_ATTR = inter_feature_link_id
    -> StrCon_13
StrCon_13: StringConcatenator
    ACTION = Overwrite Existing Attributes
    ATTRLIST = inter_feature_link_id
    PARM_LINE = fme_basicstring:19%29:InterFeatureLinkID_@Value(inter_feature_link_id)
    -> AttributeCreator_4

Bookmark: Inter Feature Links
AttributeCreator_4
    ATTR_TABLE:
      SET_TO citygml_feature_role = linkMember
      SET_TO utility_start_xlink_href = @Value(utility_start_xlink_href)
      SET_TO utility_end_xlink_href = @Value(utility_end_xlink_href)
      SET_TO utility_type = connects
    -> AttributeRenamer_11
AttributeRenamer_11
    ATTR_TABLE:
      RENAME_SET_DEFAULT network_graph_id > gml_parent_id
      RENAME_SET_DEFAULT inter_feature_link_id > gml_id
    -> utility_InterFeatureLink (writer CITYGML_1)

Bookmark: Appurtenance ID & Appurtenance Feature Graph ID
UUIDGenerator_AppurtenanceID
    UUID_ATTR = appurtenance_id
    -> StrCon_4
StrCon_4: StringConcatenator
    ACTION = Overwrite Existing Attributes
    ATTRLIST = appurtenance_id
    PARM_LINE = fme_basicstring:15%23:AppurtenanceID_@Value(appurtenance_id)
    -> UUIDGenerator_AppurtenanceFeatureGraphID
UUIDGenerator_AppurtenanceFeatureGraphID
    UUID_ATTR = appurtenance_feature_graph_id
    -> StrCon_5
StrCon_5: StringConcatenator
    ACTION = Overwrite Existing Attributes
    ATTRLIST = appurtenance_feature_graph_id
    PARM_LINE = fme_basicstring:27%37:AppurtenanceFeatureGraphID_@Value(appurtenance_feature_graph_id)
    -> AC_Appurtenance_FeatureGraph_FeatureRole
    -> AttributeRenamer_20
    -> AttributeCreator_10

Bookmark: Nodes of appurtenances (Exterior, no choice here)
AttributeCreator_10
    ATTR_TABLE:
      SET_TO citygml_lod_name = realization
      SET_TO citygml_feature_role = nodeMember
      SET_TO utility_type = exterior
    -> AttributeRenamer_23
AttributeRenamer_23
    ATTR_TABLE = RENAME_SET_DEFAULT node_fitting_intersection_id > gml_id
    -> AttributeRenamer_22
AttributeRenamer_22
    ATTR_TABLE = RENAME_SET_DEFAULT node_appurtenance_id > gml_id
    -> AttributeRenamer_24
AttributeRenamer_24
    ATTR_TABLE = RENAME_SET_DEFAULT node_fitting_adjacent_id > gml_id
    -> AttributeRenamer_25
AttributeRenamer_25
    ATTR_TABLE = RENAME_SET_DEFAULT appurtenance_feature_graph_id > gml_parent_id
    -> GeometryPropertySetter_5
GeometryPropertySetter_5
    OVERWRITE_CHOICE = Yes
    REMOVE_ATTRIBUTE = No
    SETTYPE_PARAM = Traits From Attributes
    SRC_ATTRS = citygml_lod_name
    SET -> utility_Node (writer CITYGML_1)

Bookmark: Appurtenances
AttributeRenamer_20
    ATTR_TABLE:
      RENAME_SET_DEFAULT network_id > gml_parent_id
      RENAME_SET_DEFAULT appurtenance_id > gml_id
    -> AttributeFilter_3
AttributeFilter_3
    ATTR_NAME = type_of_appurtenance
    ATTR_VALUES = <Empty>,<Missing>,<Null>,<Unfiltered>,fitting_intersection,fitting_adjacent,Curb Inlet Catchbasin,Endcap,Junction,Manhole,Outlet,Cleanout
    fitting_intersection -> AttributeCreator_9
    fitting_adjacent -> AttributeCreator_9
    Curb Inlet Catchbasin -> AttributeCreator_9
    Endcap -> AttributeCreator_9
    Junction -> AttributeCreator_9
    Manhole -> AttributeCreator_9
    Outlet -> AttributeCreator_9
    Cleanout -> AttributeCreator_9
AttributeCreator_9
    ATTR_TABLE:
      SET_TO utility_class = @Value(type_of_appurtenance)
      SET_TO utility_topo_graph_xlink_href = @Value(appurtenance_feature_graph_id)
      SET_TO citygml_feature_role = component
      SET_TO citygml_lod_name = lod1Geometry
    -> GeometryPropertySetter_4
GeometryPropertySetter_4
    OVERWRITE_CHOICE = Yes
    REMOVE_ATTRIBUTE = No
    SETTYPE_PARAM = Traits From Attributes
    SRC_ATTRS = citygml_lod_name
    SET -> utility_SimpleFunctionalElement (writer CITYGML_1)

Bookmark: Appurtenance Feature Graphs
AC_Appurtenance_FeatureGraph_FeatureRole: AttributeCreator
    ATTR_TABLE = SET_TO citygml_feature_role = featureGraphMember
    -> AttributeRenamer_Appurtenance_FeatureGraphIDs
AttributeRenamer_Appurtenance_FeatureGraphIDs
    ATTR_TABLE:
      RENAME_SET_DEFAULT appurtenance_feature_graph_id > gml_id
      RENAME_SET_DEFAULT network_graph_id > gml_parent_id
    -> GeometryRemover_Appurtenance_FeatureGraph
GeometryRemover_Appurtenance_FeatureGraph
    -> utility_FeatureGraph (writer CITYGML_1)

Bookmark: Alternative 1
SurfaceDraper_2
    ADDZ_TYPE = Replace Z
    DRAPE_TYPE = VERTEX
    INTERPOLATION_TYPE = AUTO
    TOLERANCE = 0
    DRAPED_FEATURES -> Offsetter_2
Offsetter_2
    MODE = Cartesian Coordinate
    XOFF = 0
    YOFF = 0
    ZOFF = -1.2
    OFFSET -> Inspector_3
Inspector_3
